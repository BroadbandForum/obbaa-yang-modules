module bbf-vomci-types {
  yang-version 1.1;
  namespace "urn:bbf:yang:bbf-vomci-types";
  prefix bbf-vomcit;

  import bbf-yang-types {
    prefix bbf-yang;
  }

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     WA Director: George Dobrowski, Morris Creek Consulting

     WA Director: Bruno Cornaglia, Vodafone";
  description
    "This module contains a collection of YANG definitions needed to
     for types used in the vOMCI solution as described in TR-451.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2023-05-19 {
     description
        "Update of the messages between the vOLTMF and the vOMCI function to
        match the published version of TR-451. For use only within the OB-BAA
        project while the standard device aggregation and vOLTMF YANG data 
        models are not used.";
     reference 
        "https://obbaa.broadband-forum.org/";
  }
  
  revision 2021-08-19 {
    description
      "Initial revision.";
    reference
      "TR-451";
  }

  // Definitions
  typedef vomci-entity-state {
    type enumeration {
      enum "disabled-general" {
        description
          "Indicates the entity is disabled";
      }
      enum "enabled" {
        description
          "Indicates the entity is enabled";
      }
    }
    description
      "The vOMCI entity state.";
  }

  typedef onu-alignment-status {
    type enumeration {
      enum aligned {
        value 1;
        description
          "The ONU state is aligned.";
      }
      enum unaligned {
        value 2;
        description
          "The ONU state is unaligned.";
      }
    }
    description
      "The types of ONU alignment status";
  }

  typedef onu-discovery-result {
    type enumeration {
      enum successful {
        description
          "The ONU discovery procedure was successful.";
      }
      enum failed-connectivity {
        description
          "The ONU discovery procedure failed to discover the ONU
           because the ONU is not reachable.";
      }
      enum failed-unknown {
        description
          "The ONU discovery procedure failed to discover the ONU
           because the ONU is not known to the vOLTMF.";
      }
    }
    //enumeration
    description
      "The types of ONU discover results";
  }

  typedef onu-password {
    type string {
      length "0..10";
    }
    description
      "The TC Layer ONU password.";
  }

  typedef onu-vendor-id {
    type string {
      pattern '[a-zA-Z]{4}';
    }
    description
      "The vendor id portion of the TC layer ONU-id.";
  }

  typedef onu-name {
    type bbf-yang:string-ascii64;
    description
      "The name assigned to an ONU for use in communication between 
       the vOLTMF and vOMCI function.";
  }
  
  typedef omci-sequence-number {
    type uint16;
    description
      "The omci command sequence number for the OMCI message.";
  }
  
  typedef olt-name {
    type bbf-yang:string-ascii64;
    description
      "The name assigned to the OLT device.";
  }

  typedef onu-vendor-software-version {
    type bbf-yang:string-ascii64;
    description
      "The vendor and software version for a vendor formatted
       as 'vendor_id-software_version'.";
  }
 
  //added from the published version of TR-451
  identity xpon-onu-type {
    description
      "The vOMCI ONU xPON types.";
  }
  
  identity ngpon2 {
    base xpon-onu-type;
    description
      "This denotes a NG-PON2 ONU, per ITU-T G.989.3.";
    reference
      "ITU-T G.989.3";
  }
  
  identity xgs {
    base xpon-onu-type;
    description
      "This denotes an XGS ONU, per ITU-T G.9807.1.";
    reference
      "ITU-T G.9807.1";
  }
  
  identity xgpon {
    base xpon-onu-type;
    description
      "This denotes a XG-PON ONU, per ITU-T G.987.3.";
    reference
      "ITU-T G.987.3";
  }
  
  identity gpon {
    base xpon-onu-type;
    description
      "This denotes a GPON ONU, per ITU-T G.984.3.";
    reference
      "ITU-T G.984.3";
  }
  //end of added from the published version of TR-451

  typedef onu-management-chain-selection {
    type enumeration {
      enum vomci-policy {
        description
          "Identifies that the ONU management chain is computed 
           using a policy to select the vOMCI function instance.";
      }
      enum configured {
        description
          "Identifies that the ONU management chain is configured by 
           an external entity.";
      }
      enum vomci-function {
        description
          "Identifies that the ONU management chain is computed 
           using the type of vOMCI function to select the vOMCI 
           function instance.";
      }
    }
    description
      "The types of ONU discover results";
  }

  typedef vomci-entity-type {
    type enumeration {
      enum voltmf {
        description
          "Identifies the type of vOMCI entity as a Virtualized OLT
           Management Function.";
      }
      enum onu-management-proxy {
        description
          "Identifies the type of vOMCI entity as an ONU Management 
           Proxy.";
      }
      enum vomci-function {
        description
          "Identifies the type of vOMCI entity as a Virtualized OMCI
           function.";
      }
      enum vomci-proxy {
        description
          "Identifies the type of vOMCI entity as a Virtualized OMCI
           Proxy.";
      }
      enum olt {
        description
          "Identifies the type of vOMCI entity as an OLT.";
      }
    }
    description
      "The types of entities in the vOMCI solution.";
  }

  // Identities
  // vOMCI communication identities
  identity vomci-communication-status {
    description
      "The communication status between to remote points that
       communicate to exchange vOMCI messages.";
  }
  identity connection-active {
    base vomci-communication-status;
    description
      "The connection between the remote endpoints is active.";
  }
  identity connection-inactive {
    base vomci-communication-status;
    description
      "The connection between the two endpoints is not active.";
  }
  identity remote-endpoint-is-not-assigned {
    base vomci-communication-status;
    description
      "The connection to a remote endpoint is not assigned.";
  }
  identity vomci-communication-failure {
    base vomci-communication-status;
    description
      "The remote endpoint connection is active but the endpoint 
       cannot exchange vOMCI messages with the remote endpoint.";
  }
  identity unspecified-failure {
    base vomci-communication-status;
    description
      "The endpoint cannot communicate with the remote endpoint
       to exchange vOMCI messages for an unspecified reason.";
  }

  // vOMCI Network function capabilities
  identity vomci-network-function-capability {
    description
      "Base identity for defining the capabilities of a vOMCI 
       entity.";
  } 
  identity stateful-vomci-network-function {
    base vomci-network-function-capability; 
    description
      "Identity for that describes the network function as 
       stateful.";
  }
  identity replica-vomci-network-function {
    base vomci-network-function-capability; 
    description
      "Identity for that describes the network function as 
       supporting replicas.";
  }
}
