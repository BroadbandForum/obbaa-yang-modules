module bbf-network-function-types {
  yang-version 1.1;
  namespace "urn:bbf:yang:bbf-network-function-types";
  prefix bbf-nft;

  import bbf-device-types {
    prefix bbf-dvct;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on remote network
     functions as applicable to access network equipment. As such,
     this module is specific to access network equipment (e.g., BBF-
     specified Access Nodes and FTTdp DPUs).
     
     Specifically, this module defines types of remote network
     functions and topologies.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-383; see
     the WT itself for full legal notices.";

  revision 2023-03-28 {
    description
      "TBD
       * Approval Date:    TBD.
       * Publication Date: TBD.";
    reference
      "TBD";
  }

  revision 2022-06-07 {
    description
      "Issue 1.
       * Approval Date:    2022-06-07.
       * Publication Date: 2022-06-07.";
    reference
      "TR-451: vOMCI Specification
               <https://www.broadband-forum.org/technical/download/
                        TR-451_Issue-1.pdf>";
  }

  // Identities
  // Network function types

  identity nf-type {
    description
      "Base identity for defining network function (NF) types.";
  }

  identity pnf-type {
    base bbf-dvct:device-type;
    base nf-type;
    description
      "Base identity from which physical network function (PNF)
       types are derived.";
  }

  identity vnf-type {
    base nf-type;
    description
      "Base identity from which specific virtual network function
       (VNF) types are derived.";
  }

  identity access-vnf-type {
    base vnf-type;
    description
      "Base identity from which specific access virtual network
       function types are derived.";
  }

  identity vomci-function {
    base access-vnf-type;
    description
      "Virtual OMCI network function.";
  }

  identity vomci-proxy {
    base access-vnf-type;
    description
      "Virtual OMCI Proxy network function.";
  }

  identity voltmf {
    base access-vnf-type;
    description
      "Virtual OLT management network function.";
  }

  identity onu-management-proxy {
    base access-vnf-type;
    description
      "ONU Management Proxy network function.";
  }

  // Network function topologies

  identity nf-topology {
    description
      "Base identity for defining the topology which connects network
       functions (NF).";
  }

  identity mesh {
    base nf-topology;
    description
      "Identity for a mesh type of topology that connects NFs.";
  }

  identity star {
    base nf-topology;
    description
      "Identity for a star type of topology that connects NFs.";
  }

  identity point-to-point {
    base nf-topology;
    description
      "Identity for a point to point type of topology that
       connects NFs.";
  }

  identity other-topology {
    base nf-topology;
    description
      "Identity for a point type of topology that connects NFs that
       is not already defined.";
  }
}
