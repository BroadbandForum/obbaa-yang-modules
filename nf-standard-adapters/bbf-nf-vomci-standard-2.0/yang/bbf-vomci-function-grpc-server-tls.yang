module bbf-vomci-function-grpc-server-tls {
  yang-version 1.1;
  namespace "urn:bbf:yang:bbf-vomci-function-grpc-server-tls";
  prefix bbf-vomci-func-grpcs-tls;

  import bbf-vomci-function {
    prefix bbf-vomci-func;
  }

  import bbf-vomci-function-grpc-server {
    prefix bbf-vomci-func-grpcs;
  }

  import ietf-tcp-server {
    prefix tcps;
  }

  import ietf-tls-server {
    prefix tlss;
  }

  organization
    "Broadband Forum <https://www.broadband-forum.org>
     SDN/NFV Work Area";
  contact
    "Comments or questions about this Broadband Forum YANG module
     should be directed to <mailto:help@broadband-forum.org>.

     Editor:      Jeff Hartley, Commscope

     Editor:      Andre Brizido, Altice Labs

     WA Director: Mengmeng Li, China Mobile

     WA Director: Bruno Cornaglia, Vodafone";
  description
    "This module contains a collection of YANG definitions for
     supporting the Broadband Forum requirements for vOMCI gRPC
     server functionality over TLS transport as described in TR-451.

     Copyright (c) 2019-2022, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2023-03-31 {
    description
      "TBD";
    reference
      "TBD";
  }

  augment "/bbf-vomci-func:vomci"
        + "/bbf-vomci-func:remote-nf"
        + "/bbf-vomci-func:nf-server"
        + "/bbf-vomci-func:listen"
        + "/bbf-vomci-func:listen-endpoint"
        + "/bbf-vomci-func:transport"
        + "/bbf-vomci-func-grpcs:grpc"
        + "/bbf-vomci-func-grpcs:grpc-server" 
        + "/bbf-vomci-func-grpcs:tcp-client-options" {
    description
      "The gRPC server connection parameters for TLS transport.";
    case tls-transport {
      description
        "Select TLS transport.";
      container tcp-server-parameters {
        description
          "The TCP configuration.";
        uses tcps:tcp-server-grouping;
      }
      container tls-server-parameters {
        description
          "The TLS configuration.";
        uses tlss:tls-server-grouping;
      }
    }
  }
}
