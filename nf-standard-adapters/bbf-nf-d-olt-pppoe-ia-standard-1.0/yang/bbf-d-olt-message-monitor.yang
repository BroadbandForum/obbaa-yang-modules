module bbf-d-olt-message-monitor {
  yang-version 1.1;
  namespace "urn:bbf:yang:bbf-d-olt-message-monitor";
  prefix bbf-d-olt-msg-mon;
  
  import ietf-yang-types {
    prefix yang;
  }

  organization
    "Broadband Forum <https://www.broadband-forum.org>
     SDN/NFV Work Area";
  contact
    "Comments or questions about this Broadband Forum YANG module
     should be directed to <mailto:help@broadband-forum.org>.

     Editor:      Jeff Hartley, Commscope

     Editor:      

     WA Director: Mengmeng Li, China Mobile

     WA Director: Bruno Cornaglia, Vodafone";
  description
    "This module contains a collection of YANG definitions for
     supporting the Broadband Forum requirements for monitoring
     the Disaggregated OLT (D-OLT) message interactions between the
     D-OLT and physical OLT (pOLT) Mfc interfaces as described in 
     TR-477.

     Copyright (c) 2022-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-477; see
     the TR itself for full legal notices.";

  revision 2023-03-08 {
    description
      "TBD";
    reference
      "TBD";
  }
  

  // Groupings
  grouping d-olt-message-statistics {
    description
      "Statistics for monitoring Mfc messages between D-OLT to pOLT.";
    leaf in-messages {
      type yang:counter64;
      units "messages";
      config false;
      description
        "The number of messages that have been received by the
         entity.";
    }
    leaf out-messages {
      type yang:counter64;
      units "messages";
      config false;
      description
        "The number of messages that have been transmitted by the 
         entity.";
    }
    leaf in-errored-messages {
      type yang:counter64;
      units "messages";
      config false;
      description
        "The number of messages received by the entity that contain
         errors.";
    }
  }
}
