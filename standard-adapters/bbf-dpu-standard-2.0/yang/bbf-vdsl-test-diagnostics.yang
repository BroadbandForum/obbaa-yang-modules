submodule bbf-vdsl-test-diagnostics {
  yang-version 1.1;
  belongs-to bbf-vdsl {
    prefix bbf-vdsl;
  }

  import ietf-interfaces {
    prefix if;
  }
  import bbf-fastdsl {
    prefix bbf-fastdsl;
  }
  include bbf-vdsl-base-body;
  include bbf-vdsl-xtu-sub-carrier-status-body;
  include bbf-vdsl-xtu-data-gathering-report-body;
  include bbf-vdsl-line;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG data types and
     grouping definitions for the management of VDSL test modes.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef loop-diagnostics-result {
    type enumeration {
      enum no-loop-diagnostics-results-available {
        description
          "No measurement results are available when no Loop
           Diagnostics mode procedures has been performed yet or
           after Loop Diagnostics mode results have been
           deleted.";
      }
      enum loop-diagnostics-failed-results-invalid {
        description
          "Loop Diagnostics mode results are invalid after the
           most recent Loop Diagnostics mode procedures failed.";
      }
      enum loop-diagnostics-succeeded-results-valid {
        description
          "Loop Diagnostics mode results are valid after the
           most recent Loop Diagnostics mode procedures
           succeeded.";
      }
    }
    description
      "The overall results of the Loop Diagnostics mode.";
    reference
      "ITU-T G.997.1 Clause 7.5.1.45 (LDR)";
  }

  augment "/if:interfaces-state/if:interface/bbf-fastdsl:line/bbf-"
        + "vdsl:line" {
    description
      "xDSL Testing / Diagnostics.";
    container diagnostics {
      description
        "xDSL Testing / Diagnostics.";
      leaf loop-diagnostics-mode-status {
        type enumeration {
          enum inactive {
            description
              "Loop Diagnostics mode procedures are inhibited.";
          }
          enum loop-diagnostics-ongoing {
            description
              "Loop Diagnostics mode procedures are ongoing.";
          }
        }
        description
          "Reports the status of the Loop Diagnostics mode procedures

           Upon the near-end xDSL Transceiver Unit (xTU) being forced
           to perform the Loop Diagnostic mode procedures, the Loop
           Diagnostic mode Status (LDS) shall become
           'loop-diagnostics-ongoing'.

           Upon failure or successful completion of the Loop
           Diagnostics mode procedures, the Loop Diagnostic mode
           Status (LDS) shall become 'inactive' and the Access Node
           (AN)/Distribution Point Unit (DPU) Maintenance Entity (ME)
           shall send a notification to the NMS.";
        reference
          "ITU-T G.997.1 Clause 7.5.1.44 (LDS)";
      }
      leaf loop-diagnostics-mode-results {
        type loop-diagnostics-result;
        description
          "The overall results of the Loop Diagnostics mode.";
        reference
          "ITU-T G.997.1 Clause 7.5.1.45 (LDR)";
      }
      notification loop-diagnostics-completed {
        description
          "Notifies that the loop diagnostics have completed.";
        leaf result {
          type loop-diagnostics-result;
          mandatory true;
          description
            "The overall results of the Loop Diagnostics mode.";
          reference
            "ITU-T G.997.1 Clause 7.5.1.45 (LDR)";
        }
      }
      container xtu-c {
        description
          "Diagnostics objects for the xDSL Transceiver Unit -
           Central office (xTU-C).";
        container downstream {
          description
            "Downstream xDSL Transceiver Unit (xTU) Sub-Carrier
             status.";
          uses transmit-psd;
          uses xlin;
        }
        container upstream {
          description
            "Upstream xDSL Transceiver Unit (xTU) Sub-Carrier
             status.";
          uses xtu-sub-carrier-status;
          uses xlin;
        }
        container data-gathering-report {
          description
            "Reports data gathered by the receiver.";
          uses xtu-data-gathering-report;
        }
      }
      container xtu-r {
        description
          "Diagnostics objects for the xDSL Transceiver Unit -
           Remote side (xTU-R).";
        container downstream {
          description
            "Downstream xDSL Transceiver Unit (xTU) Sub-Carrier
             status.";
          uses xtu-sub-carrier-status;
        }
        container upstream {
          description
            "Upstream xDSL Transceiver Unit (xTU) Sub-Carrier
             status.";
          uses transmit-psd;
        }
        container data-gathering-report {
          description
            "Reports data gathered by the receiver.";
          uses xtu-data-gathering-report;
        }
      }
    }
  }
}
