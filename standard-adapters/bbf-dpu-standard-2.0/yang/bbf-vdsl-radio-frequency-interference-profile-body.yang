submodule bbf-vdsl-radio-frequency-interference-profile-body {
  yang-version 1.1;
  belongs-to bbf-vdsl {
    prefix bbf-vdsl;
  }

  include bbf-vdsl-base-body;
  include bbf-vdsl-line-spectrum-profile-body;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing Broadband Forum TR-252i3 clause 5.6 Spectrum related
     profiles; Radio Frequency Interference (RFI) Profile.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping radio-frequency-interference-profile {
    description
      "Radio Frequency Interference (RFI) notches are necessary when
       radio services may be disturbed during operation, or to protect
       DSL Lines from RFI.";
    list rfibands {
      key "start-index";
      max-elements 16;
      uses sub-carrier-range;
      description
        "For [ITU-T G.992.5], this configuration parameter
         defines the subset of downstream Power Spectral Density (PSD)
         mask breakpoints, as specified in PSDMASK, that will be used
         to notch an Radio Frequency Interference (RFI) band. This
         subset consists of couples of consecutive subcarrier indices
         belonging to breakpoints: [ti; ti + 1], corresponding to the
         low level of the notch. The specific interpolation around
         these points is defined in the relevant Recommendations
         (e.g., [ITU-T G.992.5]).
         The CO-MIB will define the RFI notches using breakpoints
         in PSDMASKds as specified in the relevant
         Recommendations (e.g., [ITU-T G.992.5]).
         For [ITU-T G.993.2], this configuration parameter
         defines the bands where the PSD will be reduced as
         specified in clause 7.2.1.2 of [ITU-T G.993.2]. Each
         band will be represented by a start and stop subcarrier
         indices with a subcarrier spacing of 4.3125 kHz. Up to
         16 bands may be specified. This parameter defines the
         RFI bands for both upstream and downstream directions.
         The default is an empty list indicating no RFI bands.";
      reference
        "ITU-T G.997.1 clause 7.3.1.2.10 RFI bands (RFIBANDS)";
    }
  }

  // end grouping radio-frequency-interference-profile
}
