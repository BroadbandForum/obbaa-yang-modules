submodule bbf-vdsl-noise-margin-profile-body {
  yang-version 1.1;
  belongs-to bbf-vdsl {
    prefix bbf-vdsl;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing Broadband Forum TR-252i3 clause 5.7 DSL Quality
     Management related profiles; SNR Margin Profile.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping noise-margin-profile {
    description
      "Noise margins are important for line robustness and can be
       configured independently from other spectrum related
       parameters to reduce the amount of combinations.";
    leaf minimum-noise-margin {
      type uint16 {
        range "0..310";
      }
      units "0.1 dB";
      must '. <= ../target-noise-margin' {
        description
          "The minimum noise margin must be less than or equal to
           the target noise margin.";
      }
      default "0";
      description
        "This is the minimum noise margin the receiver will
         tolerate. If the noise margin falls below this level,
         the receiver requests the transmitter to increase the
         transmit power. If an increase to transmit power is not
         possible, a loss-of-margin (LOM) defect occurs, the
         receiver will fail and attempt to re-initialize and the
         NMS will be notified. The minimum noise margin ranges
         from 0 to 31 dB, with 0.1 dB steps.";
      reference
        "ITU-T G.997.1 clause 7.3.1.3.5 Downstream minimum noise
         margin (MINSNRMds) and clause 7.3.1.3.6 Upstream minimum
         noise margin (MINSNRMus)";
    }
    leaf target-noise-margin {
      type uint16 {
        range "0..310";
      }
      units "0.1 dB";
      must "../maximum-noise-margin = 'unbounded' or
            . <= ../maximum-noise-margin" {
          description
            "If the maximum noise margin is not unbounded, the target
             noise margin must be less than or equal to the maximum
             noise margin.";
      }
      default "60";
      description
        "This is the noise margin that the receiver will achieve,
         relative to the Bit Error Rate (BER) requirement for each of
         the bearer channels, or better, to successfully complete
         initialization. The target noise margin ranges from 0 to
         31 dB, with 0.1 dB steps.";
      reference
        "ITU-T G.997.1 clause 7.3.1.3.1 Downstream target noise
         margin (TARSNRMds) and clause 7.3.1.3.2 Upstream target
         noise margin (TARSNRMus)";
    }
    leaf maximum-noise-margin {
      type union {
        type uint16 {
          range "0..310";
        }
        type enumeration {
          enum unbounded {
            description
              "Indicates that no delay variation bound is imposed.";
          }
        }
      }
      units "0.1 dB";
      default "unbounded";
      description
        "This is the maximum noise margin the receiver will try
         to sustain. If the noise margin is above this level, the
         receiver will request the transmitter to reduce the
         transmit power to get a noise margin below this limit
         (if this functionality is supported by the relevant DSL
         Recommendation). The maximum noise margin ranges from 0
         to 31 dB with 0.1 dB steps.
         A special value (enum unbounded) is used to indicate that
         a reduction in transmit power is not required for the
         purpose of reducing the noise margin below the maximum
         noise margin limit (i.e., the maximum noise margin value
         is unbounded).";
      reference
        "ITU-T G.997.1 clause 7.3.1.3.3 Downstream maximum noise
         margin (MAXSNRMds) and clause 7.3.1.3.4 Upstream maximum
         noise margin (MAXSNRMus";
    }
    leaf ra-mode {
      type enumeration {
        enum 1 {
          description
            "Mode 1 = MANUAL.";
        }
        enum 2 {
          description
            "Mode 2 = AT_INIT.";
        }
        enum 3 {
          description
            "Mode 3 = DYNAMIC.";
        }
        enum 4 {
          description
            "Mode 4 = DYNAMIC with SOS.";
        }
      }
      default "4";
      description
        "This parameter specifies the mode of operation of a
         rate-adaptive xDSL Transceiver Unit (xTU) in the transmit 
         direction. The parameter is used only if the rate-adaptive
         functionality is supported.
         The default is enum 4, corresponding to Mode 4
         = DYNAMIC with SOS.";
      reference
        "ITU-T G.997.1 ITU-T G.997.1 clause 7.3.1.4.1 Downstream
         rate adaptation mode (RA-MODEds) and clause 7.3.1.4.2
         Upstream rate adaptation mode (RA-MODEus)";
    }
    leaf upshift-noise-margin {
      type uint16 {
        range "0..310";
      }
      units "0.1 dB";
      must "(../ra-mode != '3' and ../ra-mode != '4') or
            (. >= ../target-noise-margin and
            (../maximum-noise-margin = 'unbounded' or
            . <= ../maximum-noise-margin))" {
          description
            "If the RA-MODE is equal to 3 or 4, the upshift target
             noise margin must be greater than or equal to the
             target noise margin and less than or equal to the
             maximum noise margin.";
      }
      default "70";
      description
        "If the noise margin is above the downstream upshift
         noise margin and stays above that for more than the time
         specified by the minimum upshift rate adaptation
         interval, the receiver will attempt to increase the net
         data rate. The upshift noise margin ranges from 0 to 31
         dB, with 0.1 dB steps.";
      reference
        "ITU-T G.997.1 clause 7.3.1.4.3 Downstream upshift noise
         margin (RA-USNRMds) and clause 7.3.1.4.4 Upstream
         upshift noise margin (RA-USNRMus)";
    }
    leaf minimum-time-interval-upshift-sra {
      type uint16 {
        range "0..16383";
      }
      units "second";
      default "8";
      description
        "This parameter defines the interval of time the noise
         margin should stay above the upshift noise margin before
         the receiver will attempt to increase the net data rate.
         The time interval ranges from 0 to 16,383 s with steps
         of one second.";
      reference
        "ITU-T G.997.1 clause 7.3.1.4.5 Downstream minimum time
         interval for upshift rate adaptation (RA-UTIMEds) and
         clause 7.3.1.4.6 Upstream minimum time interval for
         upshift rate adaptation (RA-UTIMEus)";
    }
    leaf downshift-noise-margin {
      type uint16 {
        range "0..310";
      }
      units "0.1 dB";
      must "(../ra-mode != '3' and ../ra-mode != '4') or
            (. >= ../minimum-noise-margin and
            . <= ../target-noise-margin)" {
          description
            "If the RA-MODE is equal to 3 or 4, the downshift target
             noise margin must be greater than or equal to the minimum
             noise margin and less than or equal to the target noise
             margin.";
      }
      default "50";
      description
        "If the noise margin is below the noise margin and stays
         below that for more than the time specified by the
         minimum rate adaptation interval in the direction of
         transmission, the receiver will attempt to decrease the
         net data rate. The downshift noise margin ranges from 0
         to 31 dB, with 0.1 dB steps.";
      reference
        "ITU-T G.997.1 clause 7.3.1.4.7 Downstream downshift
         noise margin (RA-DSNRMds) and clause 7.3.1.4.8 Upstream
         downshift noise margin (RA-DSNRMus)";
    }
    leaf minimum-time-interval-downshift-sra {
      type uint16 {
        range "0..16383";
      }
      units "second";
      default "2";
      description
        "This parameter defines the interval of time the noise
         margin should stay below the downshift noise margin in
         the direction of transmission before the receiver will
         attempt to decrease the net data rate. The time interval
         ranges from 0 to 16,383 s with steps of one second.";
      reference
        "ITU-T G.997.1 clause 7.3.1.4.9 Downstream minimum time
         interval for downshift rate adaptation (RA-DTIMEds) and
         clause 7.3.1.4.10 Upstream minimum time interval for
         downshift rate adaptation (RA-DTIMEus)";
    }
  }

  grouping noise-margin-profile-upstream {
    description
      "Noise margin configuration nodes for the upstream noise
       margin profile.";
    uses noise-margin-profile;
    leaf snr-mode {
      type enumeration {
        enum 1 {
          description
            "If Signal-to-Noise Ratio mode (SNRMODE) equals 1, the
             virtual noise is disabled.";
        }
        enum 2 {
          description
            "If Signal-to-Noise Ratio mode (SNRMODE) equals 2, the
             transmitter-referred virtual noise is enabled.";
        }
        enum 3 {
          description
            "If Signal-to-Noise Ratio mode (SNRMODE) equals 3, the
             receiver-referred virtual noise is enabled.";
        }
        enum 4 {
          description
            "If Signal-to-Noise Ratio mode (SNRMODE) equals 4, the
             receiver-referred virtual noise together with the virtual
             noise scaling factor is enabled.";
        }
      }
      default "1";
      description
        "This parameter enables the virtual noise.";
      reference
        "ITU-T G.997.1 clause 7.3.1.7.2 Upstream signal-to-noise
         ratio mode (SNRMODEus).";
    }
  }

  grouping noise-margin-profile-downstream {
    description
      "Noise margin configuration nodes for the downstream noise
       margin profile.";
    uses noise-margin-profile;
    leaf snr-mode {
      type enumeration {
        enum 1 {
          description
            "If Signal-to-Noise Ratio mode (SNRMODE) equals 1, the
             virtual noise is disabled.";
        }
        enum 2 {
          description
            "If Signal-to-Noise Ratio mode (SNRMODE) equals 2, the
             virtual noise is enabled.";
        }
        enum 4 {
          description
            "If Signal-to-Noise Ratio mode (SNRMODE) equals 4, the
             virtual noise together with the virtual noise scaling
             factor is enabled.";
        }
      }
      default "1";
      description
        "This parameter enables the virtual noise.";
      reference
        "ITU-T G.997.1 clause 7.3.1.7.1 Downstream
         signal-to-noise ratio mode (SNRMODEds)";
    }
  }
}
