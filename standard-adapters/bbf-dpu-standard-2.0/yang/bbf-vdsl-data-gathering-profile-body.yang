submodule bbf-vdsl-data-gathering-profile-body {
  yang-version 1.1;
  belongs-to bbf-vdsl {
    prefix bbf-vdsl;
  }

  include bbf-vdsl-base-body;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing Broadband Forum TR-252i3 clause 5.7 DSL Quality
     Management related profiles; Data Gathering Profile.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping data-gathering-profile {
    description
      "These parameters are used to configure data gathering
       functionality.";
    list logging-depth-event-percentage-o {
      key "event-number";
      leaf event-number {
        type uint8;
        description
          "Identifies the event type at the VDSL Transceiver Unit - 
           central Office (VTU-O) as defined in ITU-T G.993.2 Table 
           11-43.";
      }
      leaf percentage {
        type uint8 {
          range "0..200";
        }
        units "0.5 percent";
        default "0";
        description
          "This parameter is the percentage of the data gathering
           event buffer assigned to the event type.";
      }
      description
        "This parameter is the percentage of the data gathering
         event buffer assigned to event type i at the VDSL Transceiver
         Unit - central Office (VTU-O). The ID, i, of the event type 
         is defined in Table 11-43 of [ITU-T G.993.2]. Values are 
         expressed in increments of 0.5% from 0 to 100%.";
      reference
        "ITU-T G.997.1 clause 7.3.6.1 Logging depth event
         percentage per event VTU-O
         (LOGGING_DEPTH_EVENT_PERCENTAGE_Oi)";
    }
    leaf logging-depth-reporting-o {
      type uint32;
      units "6-byte data gathering records";
      default "0";
      description
        "This parameter is the logging depth that is requested for
         reporting the VDSL Transceiver Unit - central Office (VTU-O) 
         event trace buffer in the Central Office Management 
         Information Base (CO-MIB), in number of 6-byte data gathering
         records.";
      reference
        "ITU-T G.997.1 clause 7.3.6.3 Logging depth for VTU-O
         reporting (LOGGING_DEPTH_REPORTING_O)";
    }
    list logging-depth-event-percentage-r {
      key "event-number";
      leaf event-number {
        type uint8;
        description
          "Identifies the event type as defined in
           ITU-T G.993.2 Table 11-43.";
      }
      leaf percentage {
        type uint8 {
          range "0..200";
        }
        units "0.5 percent";
        default "0";
        description
          "This parameter is the percentage of the data gathering
           event buffer assigned to the event type for the VDSL 
           Transceiver Unit - remote Side (VTU-R).";
      }
      description
        "This parameter is the percentage of the data gathering
         event buffer assigned to event type i at the VDSL Transceiver
         Unit - remote Side (VTU-R). The ID, i, of the event type is 
         defined in Table 11-43 of [ITU-T G.993.2]. Values are 
         expressed in increments of 0.5% from 0 to 100%.";
      reference
        "ITU-T G.997.1 clause 7.3.6.2
         Logging depth event percentage per event VTU-R
         (LOGGING_DEPTH_EVENT_PERCENTAGE_Ri)";
    }
    leaf logging-depth-reporting-r {
      type uint32;
      units "6-byte data gathering records";
      default "0";
      description
        "This parameter is the logging depth that is requested for
         reporting the VDSL Transceiver Unit - remote Side (VTU-R) 
         event trace buffer in the Central Office Management 
         Information Base (CO-MIB), in number of 6-byte data gathering
         records.";
      reference
        "ITU-T G.997.1 clause 7.3.6.4 Logging depth for VTU-R
         reporting";
    }
    leaf logging-report-newer-first {
      type boolean;
      default "false";
      description
        "If true, this parameter instructs the VDSL Transceiver Unit -
         remote Side (VTU-R) to report newer events first, from the 
         beginning of the event trace buffer. If false, this parameter
         instructs the VTU-R to report older events first, from the 
         end of the event trace buffer. This parameter only applies to
         the VTU-R.";
      reference
        "ITU-T G.997.1 clause 7.3.6.5 Logging data report newer
         events first VTU-R (LOGGING_REPORT_NEWER_FIRST)";
    }
  }

  // end grouping data-gathering-profile
}
