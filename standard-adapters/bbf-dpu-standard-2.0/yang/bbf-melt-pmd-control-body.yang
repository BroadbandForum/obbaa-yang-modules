submodule bbf-melt-pmd-control-body {
  yang-version 1.1;
  belongs-to bbf-melt {
    prefix bbf-melt;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing the Physical Medium Dependent (PMD) control object.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef pmd-function {
    type enumeration {
      enum measurement {
        value 1;
        description
          "Triggers the Metallic Line Test Physical Medium Dependent
           (MELT-PMD) to start the test or tests specified by the
           measurement class (MELT-MCLASS).";
      }
      enum pair-identification-tone-generation {
        value 2;
        description
          "Triggers the Metallic Line Test Physical Medium Dependent
           (MELT-PMD) to start a Pair Identification Tone (PIT)
           generation.";
      }
    }
    description
      "The MELT PMD function.";
  }

  grouping melt-pmd-control {
    description
      "Defines the parameters contained in the Physical Medium
       Dependent (PMD) control object.";
    choice pmd-functions {
      default "all-functions-disable";
      status deprecated;
      description
        "Options for enabling/disabling Physical Medium Dependent
         (PMD) functions.";
      case all-functions-disable {
        status deprecated;
        leaf all-functions-disable {
          type empty;
          status deprecated;
          description
            "Disable all Physical Medium Dependent (PMD) control
             functions.";
        }
      }
      case measurement-enable-c {
        status deprecated;
        leaf measurement-enable-c {
          type empty;
          status deprecated;
          description
            "Enables the test or tests specified by the measurement
             class (MELT-MCLASS).";
        }
      }
      case pair-identification-tone-generation-enable {
        status deprecated;
        leaf pair-identification-tone-generation-enable {
          type empty;
          status deprecated;
          description
            "Enables pair identification tone generation.";
        }
      }
    }
  }

  grouping pmd-control {
    description
      "Physical Medium Dependent (PMD) control functions.";
    leaf pmd-control {
      type enumeration {
        enum disable {
          description
            "The Metallic Line Test Physical Medium Dependent
             (MELT-PMD) functionality is not configured for a
             measurement or Pair Identification Tone (PIT)
             generation.";
        }
        enum enable {
          description
            "The Metallic Line Test Physical Medium Dependent
             (MELT-PMD) functionality is configured for a
             measurement or Pair Identification Tone (PIT)
             generation.";
        }
      }
      default "disable";
      description
        "This parameter configures the Metallic Line Test Physical
         Medium Dependent (MELT-PMD) for a MELT measurement or Pair
         Identification Tone (PIT) generation.";
    }
    action request-pmd-function-c {
      description
        "Requests to disable or enable PMD functions.";
      input {
        leaf pmd-function {
          type union {
            type enumeration {
              enum abort {
                value 0;
                description
                  "Triggers the Metallic Line Test Physical Medium
                   Dependent (MELT-PMD) to abort any ongoing
                   measurement or Pair Identification Tone (PIT)
                   generation.";
              }
            }
            type pmd-function;
          }
          description
            "A measurement or Pair Identification Tone (PIT)
             generation is by default not triggered. A measurement or
             PIT generation is triggered when the action is sent with
             the appropriate function specified. One or more
             measurements or PIT generations may be triggered while
             the Metallic Line Test Physical Medium Dependent
             (MELT-PMD) is configured 'enable', possibly with
             different MELT PMD configuration parameters. If the
             triggered measurement or PIT generation cannot be
             executed, then the Access Node/Distribution Point Unit
             (AN/DPU) Management Entitiy (ME) rejects this action and
             the  MELT PMD status remains 'inactive'.";
        }
      }
    }
  }
}
