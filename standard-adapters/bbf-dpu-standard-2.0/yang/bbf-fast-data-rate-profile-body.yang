submodule bbf-fast-data-rate-profile-body {
  yang-version 1.1;
  belongs-to bbf-fast {
    prefix bbf-fast;
  }

  import bbf-yang-types {
    prefix bbf-yang;
  }
  include bbf-fast-base;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing data rate profiles.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping data-rate-parameters {
    description
      "Data rate configuration parameters.";
    reference
      "ITU-T G.997.2 clause 7.2.1.";
    leaf maximum-net-data-rate {
      type bbf-yang:data-rate32;
      default "4294967295";
      description
        "Defines the value of the maximum net data rate (see clause
         11.4.2.2/G.9701).";
      reference
        "ITU-T G.997.2 clause 7.2.1.1 (MAXNDR).";
    }
    leaf minimum-expected-throughput {
      type bbf-yang:data-rate32;
      must '. < ../maximum-net-data-rate' {
        description
          "The minimum expected throughput must be less than the
           maximum net data rate.";
      }
      default "0";
      description
        "Defines the value of the minimum expected throughput (see
         clause 11.4.2.1/G.9701).";
      reference
        "ITU-T G.997.2 clause 7.2.1.2 (MINETR).";
    }
    leaf maximum-gamma-data-rate {
      type bbf-yang:data-rate32;
      must '. >= ../minimum-gamma-data-rate' {
        description
          "The maximum gamma data rate must be greater than or equal
           to the mimimum gamma data rate.";
      }
      default "4294967295";
      description
        "Defines the maximum value of the Gamma Data Rate (GDR)
         (see clause 7.11.1.3/G.997.2). The GDR shall not exceed
         maximum Gamma Data Rate (MAXGDR) at the start of showtime
         and during showtime. ";
      reference
        "ITU-T G.997.2 clause 7.2.1.3 (MAXGDR).";
    }
    leaf minimum-gamma-data-rate {
      type bbf-yang:data-rate32;
      must '. <= ../maximum-gamma-data-rate' {
        description
          "The minimum gamma data rate must be less than or equal to
           the maximum gamma data rate.";
      }
      default "0";
      description
        "Defines the minimum value of the Gamma Data Rate (GDR)
         (see clause 7.11.1.3/G.997.2). The GDR may be lower than
         minimum Gamma Data Rate (MINGDR). If the GDR is lower than
         MINGDR at initialization or when GDR becomes lower than
         MINGDR during showtime, a threshold crossing alert occurs.";
      reference
        "ITU-T G.997.2 clause 7.2.1.4 (MINGDR).";
    }
    container preferred-ndr {
      if-feature "preferred-ndr";
      description
        "Preferred Net Data Rate (NDR) configuration.";
      leaf preferred-net-data-rate {
        type bbf-yang:data-rate32;
        default "0";
        description
          "This parameter provides the informative value of
           the Preferred Net Data Rate (PREFNDR) relating to the
           services enabled on a line. There is no normative expected
           behavior related to this parameter.";
        reference
          "ITU-T G.997.2 clause 7.2.1.5 (PREFNDR).";
      }
      leaf preferred-net-data-rate-type {
        type enumeration {
          enum high {
            description
              "Net Data Rate (NDR) should be as high as reasonably
               possible, Preferred Net Data Rate (PREFNDR) may be
               ignored.";
          }
          enum vendor-discretionary {
            description
              "Vendor discretionary interpretation of Preferred Net
               Data Rate (PREFNDR), the behavior relative to the
               configured PREFNDR is not specified.";
          }
          enum close-to {
            description
              "Net Data Rate (NDR) should be close to the Preferred
               Net Data Rate (PREFNDR).";
          }
          enum at-least {
            description
              "Net Data Rate (NDR) should be greater than or equal to
               the Preferred Net Data Rate (PREFNDR), if feasible and
               reasonable.";
          }
        }
        default "high";
        description
          "This parameter describes the interpretation of the
           Preferred Net Data Rate (PREFNDR) parameter. All lines in
           the same vectored group should be configured with a common
           value for PREFNDR_TYPEus and a common value for
           PREFNDR_TYPEds. There is no normative expected behavior
           related to this parameter.";
        reference
          "ITU-T G.9701 clause 7.2.1.6 (PREFNDR_TYPE).";
      }
    }
    container dynamic-time-assignment {
      if-feature "bbf-fast:dta";
      description
        "Configuruation of Dynamic Time Assignment (DTA).";
      leaf minimum-expected-throughput {
        type bbf-yang:data-rate32;
        must '. < ../maximum-net-data-rate' {
          description
            "The minimum expected throughput for Dynamic Time
             Assignment (DTA) must be less than the maximum net data
             rate for DTA.";
        }
        default "0";
        description
          "Defines the value of the minimum expected
           throughput for Dynamic Time Assignment (DTA) operation to
           constrain the dynamic range of Mds requested by the
           Dynamic Resource Allocation (DRA).

           If 'dta-allowed' in the Time Division Duplexing (TDD)
           profile is equal to 'cdta', then a value less than or equal
           to the minimum expected throughput without DTA operation
           must be configured.";
        reference
          "ITU-T G.9701 clause T.2.7.";
      }
      leaf maximum-net-data-rate {
        type bbf-yang:data-rate32;
        default "4294967295";
        description
          "Defines the value of the maximum Net Datat Rate (NDR) for
           Dynamic Time Assignment (DTA) operation.";
        reference
          "ITU-T G.9701 clause D.5.7.5, X.6.7.5 and T.2.8";
      }
    }
    leaf low-andeftr-threshold {
      if-feature "bbf-fast:andeftr";
      type bbf-yang:data-rate32;
      default "0";
      description
        "Defines the value of the low All NOI with Data symbols
         Error-Free Throughput Rate threshold.";
      reference
        "ITU-T G.997.2 clause 7.2.4.1 (LOW-ANDEFTR-THRESHOLD)";
    }
  }

  grouping low-power-data-rate-parameters {
    description
      "Parameters associated with configuration of data rates when
       operating in a low power mode.";
    leaf maximum-net-data-rate-in-l2.2 {
      type bbf-yang:data-rate32;
      default "4294967295";
      description
        "Defines the value of the maximum net data rate allowed
         during the L2.2 link state for both the upstream and
         downstream direction.";
      reference
        "ITU-T G.997.2 clause 7.2.3.2 (L2.2-MAXNDR); ITU-T G.9701
         clause 13.4.2.4.";
    }
    leaf minimum-expected-throughput-in-l2.2 {
      type bbf-yang:data-rate32;
      default "0";
      description
        "Defines the value of the minimum expected throughput
         allowed during the L2.2 link state for both the upstream
         and downstream direction.";
      reference
        "ITU-T G.997.2 clause 7.2.3.4 (L2.2-MINETR); ITU-T G.9701
         clause 13.4.2.4.";
    }
  }

  grouping low-power-data-rate-directional-parameters {
    description
      "Parameters associated with configuration of data rates when
       operating in a low power mode for both the upstream and
       downstream directions.";
    leaf maximum-net-data-rate-in-l2.1 {
      type bbf-yang:data-rate32;
      default "4294967295";
      description
        "Defines the value of the maximum net data rate allowed
         during the L2.1 link state.";
      reference
        "ITU-T G.997.2 clause 7.2.3.1 (L2.1-MAXNDR); ITU-T G.9701
         clause 13.4.1.4.";
    }
    leaf minimum-expected-throughput-in-l2.1 {
      type bbf-yang:data-rate32;
      default "0";
      description
        "Defines the value of the minimum expected throughput
         allowed during the L2.1 link state.";
      reference
        "ITU-T G.997.2 clause 7.2.3.3 (L2.1-MINETR); ITU-T G.9701
         clause 13.4.1.4.";
    }
    leaf minimum-expected-throughput-after-exit-from-l2.1 {
      type bbf-yang:data-rate32;
      default "0";
      description
        "Defines the value of the minimum expected throughput
         allowed after exit from L2.1 to the L0 link state.";
      reference
        "ITU-T G.997.2 clause 7.2.3.5 (L2.1-MINETR-EXIT); ITU-T
         G.9701 clause 13.4.1.4.";
    }
  }

  grouping data-rate-profile {
    description
      "Defines the parameters contained in a data rate profile.";
    uses data-rate-parameters;
  }

  grouping low-power-data-rate-profile {
    description
      "Defines the parameters contained in a low power data rate
       profile.";
    uses low-power-data-rate-parameters;
    container downstream {
      description
        "Downstream low power data rate parameters.";
      uses low-power-data-rate-directional-parameters;
    }
    container upstream {
      description
        "Upstream low power data rate parameters.";
      uses low-power-data-rate-directional-parameters;
    }
  }
}
