submodule bbf-vdsl-vectoring-profile-body {
  yang-version 1.1;
  belongs-to bbf-vdsl {
    prefix bbf-vdsl;
  }

  include bbf-vdsl-base;
  include bbf-vdsl-base-body;
  include bbf-vdsl-line-spectrum-profile-body;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing Broadband Forum TR-252i3 clause 5.7 DSL Quality
     Management related profiles; Vectoring Profile.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping vectoring-profile {
    description
      "The Vectoring mechanism is defined by ITU-T Recommendation
       G.993.5. The Vectoring Profile contains part of the Vectoring
       related configuration parameters while the rest of the
       parameters are located in the data rate profile.";
    list vector-band-control {
      key "start-index";
      max-elements 8;
      uses sub-carrier-range;
      description
        "This configuration parameter is an array of pairs of
         sub-carrier indices (a(i), b(i)). Each pair specifies a
         frequency band starting from sub-carrier index a(i) and
         ending at sub-carrier index b(i) (including both start
         and end points) in which Far-End Crosstalk (FEXT)
         cancellation for the line is not required. Up to 8 frequency
         bands may be configured. The same value of this parameter
         will be set for all lines of the same vector group.
         The default is an empty list, corresponding to no
         vectoring frequency-band control.";
      reference
        "ITU-T G.997.1 clause 7.3.1.13.1 Vectoring frequency-band
         control upstream (VECTOR_BAND_CONTROLus) and clause
         7.3.1.13.2 Vectoring frequency-band control downstream
         (VECTOR_BAND_CONTROLds)";
    }
    leaf fext-cancel-priority {
      type enumeration {
        enum LOW {
          description
            "Low priority for Far-End Crosstalk (FEXT) cancellation.";
        }
        enum HIGH {
          description
            "High priority for Far-End Crosstalk (FEXT)
             cancellation.";
        }
      }
      default "HIGH";
      description
        "This parameter specifies line priority for the line in
         the vectored group in the direction of transmission, as
         defined in [ITU-T G.993.5]. Two line priorities are
         defined as LOW and HIGH. The default is HIGH.";
      reference
        "ITU-T G.997.1 clause 7.3.1.13.3 FEXT cancellation line
         priorities upstream (FEXT_CANCEL_PRIORITYus) and clause
         7.3.1.13.4 FEXT cancellation line priorities downstream
         (FEXT_CANCEL_PRIORITYds)";
    }
    leaf fext-cancel-enable {
      type enumeration {
        enum 1 {
          description
            "Far-End Crosstalk (FEXT) cancellation enabled.";
        }
        enum 0 {
          description
            "Far-End Crosstalk (FEXT) cancellation disabled.";
        }
      }
      default "1";
      description
        "A value of 1 enables and a value of 0 disables Far-End
         Crosstalk (FEXT) cancellation in the direction of
         transmission from all the other vectored lines into the line
         in the vectored group. The default is enum 1, corresponding
         to FEXT cancellation enabled.";
      reference
        "ITU-T G.997.1 clause 7.3.1.13.5 FEXT cancellation
         enabling/disabling upstream (FEXT_CANCEL_ENABLEus) and
         clause 7.3.1.13.6 FEXT cancellation enabling/disabling
         downstream (FEXT_CANCEL_ENABLEds)";
    }
    leaf xlin-group-size-req {
      type uint8 {
        range "1 | 2 | 4 | 8 | 16 | 32 | 64";
      }
      default "1";
      description
        "This parameter is the requested value of XLIN Group size
         (XLING) in the direction of transmission. The valid values
         are 1, 2, 4, 8, 16, 32, and 64.";
      reference
        "ITU-T G.997.1 clause 7.3.1.13.7 Downstream requested
         XLIN subcarrier group size (XLINGREQds) and clause
         7.3.1.13.8 Upstream requested XLIN subcarrier group size
         (XLINGREQus)";
    }
  }

  // end grouping vectoring-profile

  grouping vectoring-profile-non-directional {
    description
      "Configuration data that is not associated with the upstream
       or downstream directions.";
    leaf vector-mode-enable {
      type union {
        type enumeration {
          enum all {
            description
              "All vector modes enabled.";
          }
        }
        type bits {
          bit bit0 {
            position 0;
            description
              "initialization in ITU-T G.993.2 mode with neither
               Annex X nor Annex Y enabled.";
          }
          bit bit1 {
            position 1;
            description
              "initialization in ITU-T G.993.2 Annex X.";
          }
          bit bit2 {
            position 2;
            description
              "initialization in ITU-T G.993.2 Annex Y.";
          }
          bit bit3 {
            position 3;
            description
              "initialization in ITU-T G.993.5.";
          }
          // bit bit4; // reserved by ITU-T
          // bit bit5; // reserved by ITU-T
          // bit bit6; // reserved by ITU-T
          // bit bit7; // reserved by ITU-T
        }
      }
      default "all";
      description
        "This configuration parameter defines the vectoring
         initialization type to be allowed by the VTU O on the
         line. The default is 'all', corresponding to all vectoring
         modes allowed.";
      reference
        "ITU-T G.997.1 clause 7.3.1.13.9 Vectoring mode enable
         (VECTORMODE_ENABLE)";
    }
    leaf strongfext-mode {
      if-feature "bbf-vdsl:strongfext";
      type enumeration {
        enum disabled {
          description
            "Operation according to G.993.5 Annex A is disable.";
        }
        enum preferred {
          description
            "Operation according to G.993.5 Annex A is preferred.";
        }
        enum forced {
          description
            "Operation according to G.993.5 Annex A is forced.";
        }
        enum forced-above-17mhz {
          description
            "Operation according to G.993.5 Annex A is forced above
             17MHz.";
        }
      }
      default "disabled";
      description
        "This configuration parameter specifies if operation
         according to G.993.5 Annex A is disabled, preferred, forced,
         or forced above 17MHz.";
      reference
        "ITU-T G.997.1 clause 7.3.1.17.1 STRONGFEXT mode";
    }
  }
}
