submodule bbf-vdsl-xtu-line-performance-body {
  yang-version 1.1;
  belongs-to bbf-vdsl {
    prefix bbf-vdsl;
  }

  import bbf-yang-types {
    prefix bbf-yang;
  }
  import ietf-yang-types {
    prefix yang;
  }
  include bbf-vdsl-base;
  include bbf-vdsl-base-body;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing Broadband Forum TR-252i3 clause 7.1 xDSL Transceiver 
     Unit (xTU) Line Performance.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping xtu-c-line-performance {
    description
      "Line performance data for a given xDSL Transceiver Unit - 
       Central office (xTU-C).";
    leaf measured-time {
      type uint32;
      description
        "Reports the amount of time, measured in seconds,
         that statistics for this interval have been counted.";
      reference
        "ITU-T G.997.2 clause 7.7.1 and 7.8.1.";
    }
    leaf invalid-data-flag {
      type boolean;
      description
        "Reports the validity of the corresponding
         performance monitoring data. true = invalid.";
      reference
        "ITU-T G.997.2 clause 7.7.2 and 7.8.2.";
    }
    leaf forward-error-correction-seconds-l {
      type bbf-yang:performance-counter32;
      description
        "This parameter is a count of 1-second intervals with one
         or more Forward Error Correction (FEC) anomalies summed over
         all received bearer channels.";
      reference
        "ITU-T G.997.1 clause 7.2.1.1.1 Forward error correction
         second - Line (FECS-L)";
    }
    leaf errored-seconds-l {
      type bbf-yang:performance-counter32;
      description
        "This parameter is a count of 1-second intervals with one
         or more Cyclic Redundancy Check (CRC-8) anomalies summed over
         all received bearer channels, or one or more Loss of Signal
         (LOS) defects, or one or more Severely Errored Frame (SEF)
         defects, or one or more Loss of Power (LPR) defects.";
      reference
        "ITU-T G.997.1 clause 7.2.1.1.2 Errored second - Line
         (ES-L)";
    }
    leaf severely-errored-seconds-l {
      type bbf-yang:performance-counter32;
      description
        "This parameter is a count of severely errored seconds
         (SES). An SES is declared if, during a 1-second
         interval, there are 18 or more Cyclic Redundancy Check
         (CRC-8) anomalies in one or more of the received bearer
         channels, or one or more Loss of Signal (LOS) defects, or one
         or more Severely Errored Frame (SEF) defects, or one or more
         Loss of Power (LPR) defects. If [ITU-T G.998.4] is supported
         and retransmission is enabled in the near-end received
         direction, a SES is also declared if, during a 1-second
         interval, there is one or more Severe Loss of Error-Free
         Throughput (SEFTR) defect in the near-end received
         direction.";
      reference
        "ITU-T G.997.1 clause 7.2.1.1.3 Severely errored second -
         Line (SES-L)";
    }
    leaf loss-of-signal-seconds-l {
      type bbf-yang:performance-counter32;
      description
        "This parameter is a count of 1-second intervals
         containing one or more Loss of Signal (LOS) defects.";
      reference
        "ITU-T G.997.1 clause 7.2.1.1.4 LOS second - Line
         (LOSS-L)";
    }
    leaf unavailable-seconds-l {
      type bbf-yang:performance-counter32;
      description
        "This parameter is a count of 1-second intervals for
         which the xDSL line is unavailable. Some parameter
         counts are inhibited during unavailability - see ITU-T
         G.997.1 clause 7.2.7.13.";
      reference
        "ITU-T G.997.1 clause 7.2.1.1.5 Unavailable second - Line
         (UAS-L)";
    }
    list inminpeq-l {
      key "inminpeq-index";
      leaf inminpeq-index {
        type uint8 {
          range "1..17";
        }
        description
          "Identifies the INMAINPEQ histogram bin.";
      }
      leaf inminpeq-l {
        type bbf-yang:performance-counter32-or-inactive;
        description
          "Count of the near-end INMAINPEQ anomalies.";
      }
      description
        "This parameter is a count of the near-end INMAINPEQi
         anomalies occurring on the line during the accumulation
         period. This parameter is subject to inhibiting - see
         ITU-T G.997.1 clause 7.2.7.13.

         A special value (enum inactive) indicates that this
         counter is not active on the line. This occurs when the
         feature 'impulse-noise-monitoring' is not supported.";
      reference
        "ITU-T G.997.1 clause 7.2.1.4.1 INM INPEQ histogram 1..17
         (INMINPEQ1..17-L)";
    }
    leaf inmme-l {
      type bbf-yang:performance-counter32-or-inactive;
      description
        "This parameter is a count of the near-end INMAME
         anomalies occurring on the line during the accumulation
         period. This parameter is subject to inhibiting - see
         ITU-T G.997.1 clause 7.2.7.13.

         A special value (enum inactive) indicates that this
         counter is not active on the line. This occurs when the
         feature 'impulse-noise-monitoring' is not supported.";
      reference
        "ITU-T G.997.1 clause 7.2.1.4.2 INM total measurement
         (INMME-L)";
    }
    list inmiat-l {
      key "inminiat-index";
      leaf inminiat-index {
        type uint8 {
          range "0..7";
        }
        description
          "Identifies the INMAIAT histogram bin.";
      }
      leaf inmiat-l {
        type bbf-yang:performance-counter32-or-inactive;
        description
          "Count of the near-end INMAIAT anomalies.";
      }
      description
        "This parameter is a count of the near-end INMAIATi
         anomalies occurring on the line during the accumulation
         period. This parameter is subject to inhibiting - see
         ITU-T G.997.1 clause 7.2.7.13.

         A special value (enum inactive) indicates that this
         counter is not active on the line. This occurs when the
         feature 'impulse-noise-monitoring' is not supported.";
      reference
        "ITU-T G.997.1 clause 7.2.1.4.3 INM IAT histogram 0..7
         (INMIAT0..7-L)";
    }
    leaf sos-success-ne {
      type bbf-yang:performance-counter32-or-inactive;
      description
        "This parameter is a count of the total number of
         successful Save our Showtime (SOS) procedures initiated by
         the near-end xDSL Transceiver Unit (xTU) on the line during 
         the accumulation period. Parameter procedures will be as 
         defined in ITU-T G.997.1 clause 7.2.7. Successful SOS is 
         defined in clause 12.1.4 of [ITU-T G.993.2].

         A special value (enum inactive) indicates that this
         counter is not active on the line. This occurs when the
         feature 'sos' is not supported.";
      reference
        "ITU-T G.997.1 clause 7.2.1.6.1 Near-end successful SOS
         count (SOS-SUCCESS-NE)";
    }
    leaf leftr-defects-seconds-counter-ne {
      type bbf-yang:performance-counter32;
      description
        "Near-end line Low Error-Free Throughput (LEFTR) defects
         seconds counter. If retransmission is used in a given
         transmit direction, this parameter is a count of the seconds
         with a near-end ''leftr'' defect present (see clause 11.4.1
         of [ITU-T G.998.4] for the definition of this counter).
         This near-end counter is only defined for upstream.";
      reference
        "ITU-T G.997.1 clause 7.2.1.1.6 leftr defects seconds
         counter";
    }
    leaf error-free-bits-counter-ne {
      type bbf-yang:performance-counter32;
      description
        "Near-end line error-free bits counter. If retransmission
         is used in a given transmit direction, this parameter is
         a count of the number of error-free bits passed over the
         Beta1 reference point, divided by 65536 = 2^16 (see
         clause 11.4.2 of [ITU-T G.998.4] for the definition of
         this counter).
         This near-end counter is only defined for upstream.";
      reference
        "ITU-T G.997.1 clause 7.2.1.1.7 Error-free bits counter";
    }
    leaf minimum-error-free-throughput-ne {
      type bbf-yang:performance-counter32;
      units "bit/s";
      description
        "Near-end Minimum Error-Free Throughput (MINEFTR). If
         retransmission is used in a given transmit direction,
         this parameter MINEFTR reports the minimum of the EFTR
         observed over the 15-min or 24-hour accumulation period
         (see clause 11.4.3 of [ITU-T G.998.4] for the definition
         of this parameter). The value is reported in bit/s.
         This near-end value is only defined for upstream.";
      reference
        "ITU-T G.997.1 clause 7.2.1.1.8 Minimum error-free
         throughput (MINEFTR)";
    }
    leaf full-initializations {
      type bbf-yang:performance-counter32;
      description
        "This parameter is a count of the total number of full
         initializations attempted on the line (successful and
         failed) during the accumulation period. Parameter
         procedures are defined in ITU-T G997.1 clause 7.2.7.";
      reference
        "ITU-T G.997.1 clause 7.2.1.3.1 Full initialization
         count";
    }
    leaf failed-full-initializations {
      type bbf-yang:performance-counter32;
      description
        "This performance parameter is a count of the total
         number of failed full initializations during the
         accumulation period. A failed full initialization is
         when showtime is not reached at the end of the full
         initialization procedure. Parameter procedures are
         defined in ITU-T G997.1 clause 7.2.7.";
      reference
        "ITU-T G.997.1 clause 7.2.1.3.2 Failed full
         initialization count";
    }
    leaf short-initializations {
      type bbf-yang:performance-counter32-or-inactive;
      description
        "This parameter is a count of the total number of fast
         retrains or short initializations attempted on the line
         (successful and failed) during the accumulation period.
         Parameter procedures are defined in ITU-T G997.1 clause
         7.2.7.

         A special value (enum inactive) indicates that this
         counter is not active on the line as this is only applicable
         when running in an ADSL mode of operation.";
      reference
        "ITU-T G.997.1 clause 7.2.1.3.3 Short initialization
         count";
    }
    leaf failed-short-initializations {
      type bbf-yang:performance-counter32-or-inactive;
      description
        "This performance parameter is a count of the total
         number of failed fast retrains or short initializations
         during the accumulation period. A failed fast retrain or
         short initialization is when showtime is not reached at
         the end of the fast retrain or short initialization
         procedure, e.g., when: A Cyclic Redundancy Check (CRC) error
         is detected, a time-out occurs, or a fast retrain profile is
         unknown. Parameter procedures are defined in ITU-T G997.1
         clause 7.2.7.

         A special value (enum inactive) indicates that this
         counter is not active on the line as this is only applicable
         when running in an ADSL mode of operation.";
      reference
        "ITU-T G.997.1 clause 7.2.1.3.4 Failed short
         initialization count";
    }
    leaf loss-of-power-intrpt {
      type bbf-yang:performance-counter32-or-inactive;
      description
        "This parameter is a count of the number of lpr_intrpt
         anomalies occurring during the accumulation period.
         Those anomalies are defined in clause 11.3.1.1 of [ITU-T
         G.993.2]. A special value (enum inactive) indicates that this
         counter is not active on the line.
         Threshold reports for this counter are not specified.";
      reference
        "ITU-T G.997.1 clause 7.2.1.8.1 Loss of Power
         interruption count (LPR_INTRPT)";
    }
    leaf host-reinit-interruptions {
      type bbf-yang:performance-counter32-or-inactive;
      description
        "This parameter is a count of the number of hri_intrpt
         anomalies occurring during the accumulation period.
         Those anomalies are defined in clause 11.3.1.1 of [ITU-T
         G.993.2]. A special value (enum inactive) indicates that this
         counter is not active on the line.
         Threshold reports for this counter are not specified.";
      reference
        "ITU-T G.997.1 clause 7.2.1.8.2 Host-Reinit interruption
         count (HRI_INTRPT)";
    }
    leaf spontaneous-intrpt {
      type bbf-yang:performance-counter32-or-inactive;
      description
        "This parameter is a count of the number of spont_intrpt
         anomalies occurring during the accumulation period.
         Those defects are defined in clause 11.3.1.1 of [ITU-T
         G.993.2]. A special value (enum inactive) indicates that this
         counter is not active on the line.
         Threshold reports are specified for the 24-hour interval
         counter only.";
      reference
        "ITU-T G.997.1 clause 7.2.1.8.3 Spontaneous interruption
         count (SPONT_INTRPT)";
    }
    leaf loss-of-signal {
      type bbf-yang:performance-counter32;
      description
        "Reports a count of the Loss of Signal (LOS) failures.";
      reference
        "Borrowed from ITU-T G.997.2 clause 7.7.4 (LOS).
         Count of failures defined in ITU-T G.997.1
         clause 7.1.1.1.1.";
    }
    leaf loss-of-frame {
      type bbf-yang:performance-counter32;
      description
        "Reports a count of the Loss of Frame (LOF) failures.";
      reference
        "Count of failures defined in ITU-T G.997.1
         clause 7.1.1.1.2.";
    }
    leaf loss-of-power {
      type bbf-yang:performance-counter32;
      description
        "reports a count of the Loss of Power (LPR) failures.";
      reference
        "Borrowed from ITU-T G.997.2 clause 7.7.7 (LPR).
         Count of failures defined in ITU-T G.997.1
         clause 7.1.1.1.3.";
    }
    leaf maximum-error-free-throughput-ne {
      if-feature "maxeftr";
      type bbf-yang:performance-counter32;
      units "bit/s";
      description
        "Near-end Maximum Error-Free Throughput (MAXEFTR). If
         retransmission is used in a given transmit direction,
         this parameter MAXEFTR reports the maximum of the EFTR
         observed over the 15-min or 24-hour accumulation period
         (see clause 11.4.4 of [ITU-T G.998.4] for the definition
         of this parameter). The value is reported in bit/s.
         This near-end value is only defined for upstream.";
      reference
        "ITU-T G.997.1 clause 7.2.1.1.9 Maximum error-free
         throughput (MAXEFTR)";
    }
    leaf sra-success-ne {
      if-feature "successful-sra";
      type bbf-yang:performance-counter32;
      description
        "This parameter is a count of the total number of
         successful Seamless Rate Adaptation (SRA) procedures
         initiated by the near-end xDSL Transceiver Unit (xTU) on the 
         line during the accumulation period. Parameter procedures 
         will be as defined in ITU-T G.997.1 clause 7.2.9. Successful 
         SRA is defined in clause 11.3.1.6 of [ITU-T G.993.2].";
      reference
        "ITU-T G.997.1 clause 7.2.9 Near-end successful SRA
         count (SRA-SUCCESS-NE)";
    }
  }

  // end grouping xtu-c-line-performance

  grouping xtu-r-line-performance {
    description
      "Line performance data for a given xDSL Transceiver Unit - 
       Remote side (xTU-R).";
    leaf measured-time {
      type uint32;
      description
        "Reports the amount of time, measured in seconds,
         that statistics for this interval have been counted.";
      reference
        "ITU-T G.997.2 clause 7.7.1 and 7.8.1.";
    }
    leaf invalid-data-flag {
      type boolean;
      description
        "Reports the validity of the corresponding
         performance monitoring data. true = invalid.";
      reference
        "ITU-T G.997.2 clause 7.7.2 and 7.8.2.";
    }
    leaf forward-error-correction-seconds-lfe {
      type bbf-yang:performance-counter32;
      description
        "This parameter is a count of 1-second intervals with one
         or more Far-End Forward Error Correction  (FFEC) anomalies
         summed over all transmitted bearer channels.";
      reference
        "ITU-T G.997.1 clause 7.2.1.2.1 Forward error correction
         second - Line far-end (FECS-LFE)";
    }
    leaf errored-seconds-lfe {
      type bbf-yang:performance-counter32;
      description
        "This parameter is a count of one-second intervals with
         one or more Far-End Block Error (FEBE) anomalies summed over
         all transmitted bearer channels, or one or more Far-End Loss
         of Signal (LOS-FE) defects, or one or more Remote Defect
         Indication (RDI) defects, or one or more Far-End Loss of
         Power (LPR-FE) defects.";
      reference
        "ITU-T G.997.1 clause 7.2.1.2.2 Errored second - Line
         far-end (ES-LFE)";
    }
    leaf severely-errored-seconds-lfe {
      type bbf-yang:performance-counter32;
      description
        "This parameter is a count of severely errored seconds
         (SES). An SES is declared if, during a 1-second
         interval, there are 18 or more Far-End Block Error (FEBE)
         anomalies in one or more of the transmitted bearer channels,
         or one or more Far-End Loss of Signal (LOS-FE) defects, or
         one or more Remote Defect Indication (RDI) defects, or one or
         more Far-End Loss of Power (LPR-FE) defects. If
         [ITU-T G.998.4] is supported and retransmission is enabled in
         the far-end received direction, a SES-LFE is also declared
         if, during a 1-second interval, there is one or more severe
         loss of error-free throughput (seftr) defect in the far-end
         received direction.";
      reference
        "ITU-T G.997.1 clause 7.2.1.2.3 Severely errored second -
         Line far-end (SES-LFE)";
    }
    leaf loss-of-signal-seconds-lfe {
      type bbf-yang:performance-counter32;
      description
        "This parameter is a count of 1-second intervals
         containing one or more far-end Loss of Signal (LOS)
         defects.";
      reference
        "ITU-T G.997.1 clause 7.2.1.2.4 LOS second - Line far-end
         (LOSS-LFE)";
    }
    leaf unavailable-seconds-lfe {
      type bbf-yang:performance-counter32;
      description
        "This parameter is a count of 1-second intervals for
         which the far-end xDSL line is unavailable. Some
         parameter counts are inhibited during unavailability -
         see ITU-T G.997.1 clause 7.2.7.13.";
      reference
        "ITU-T G.997.1 clause 7.2.1.2.5 Unavailable seconds -
         Line far-end (UAS-LFE)";
    }
    list inminpeq-lfe {
      key "inminpeq-index";
      leaf inminpeq-index {
        type uint8 {
          range "1..17";
        }
        description
          "Identifies the INMAINPEQ histogram bin.";
      }
      leaf inminpeq-lfe {
        type bbf-yang:performance-counter32-or-inactive;
        description
          "Count of the far-end INMAINPEQ anomalies.

           A special value (enum inactive) indicates that this
           counter is not active on the line. This occurs when the
           feature 'impulse-noise-monitoring' is not supported.";
      }
      description
        "This parameter is a count of the far-end INMAINPEQi
         anomalies occurring on the line during the accumulation
         period. This parameter is subject to inhibiting - see
         ITU-T G.997.1 clause 7.2.7.13.";
      reference
        "ITU-T G.997.1 clause 7.2.1.5.1 INM INPEQ histogram 1..17
         (INMINPEQ1..17-LFE)";
    }
    leaf inmme-lfe {
      type bbf-yang:performance-counter32-or-inactive;
      description
        "This parameter is a count of the far-end INMAME
         anomalies occurring on the line during the accumulation
         period. This parameter is subject to inhibiting - see
         ITU-T G.997.1 clause 7.2.7.13.

         A special value (enum inactive) indicates that this
         counter is not active on the line. This occurs when the
         feature 'impulse-noise-monitoring' is not supported.";
      reference
        "ITU-T G.997.1 clause 7.2.1.5.2 INM total measurement
         (INMME-LFE)";
    }
    list inmiat-lfe {
      key "inminiat-index";
      leaf inminiat-index {
        type uint8 {
          range "0..7";
        }
        description
          "Identifies the INMAIAT histogram bin.";
      }
      leaf inmiat-lfe {
        type bbf-yang:performance-counter32-or-inactive;
        description
          "Count of the far-end INMAIAT anomalies.

           A special value (enum inactive) indicates that this
           counter is not active on the line. This occurs when the
           feature 'impulse-noise-monitoring' is not supported.";
      }
      description
        "This parameter is a count of the far-end INMAIATi
         anomalies occurring on the line during the accumulation
         period. This parameter is subject to inhibiting - see
         ITU-T G.997.1 clause 7.2.7.13.";
      reference
        "ITU-T G.997.1 clause 7.2.1.5.3 INM IAT histogram 0..7
         (INMIAT0..7-LFE)";
    }
    leaf sos-success-fe {
      type bbf-yang:performance-counter32-or-inactive;
      description
        "This parameter is a count of the total number of
         successful Save our Showtime (SOS) procedures initiated by
         the far-end xDSL Transceiver Unit (xTU) on the line during 
         the accumulation period. Parameter procedures will be as 
         defined in ITU-T G.997.1 clause 7.2.7. Successful SOS is 
         defined in clause 12.1.4 of [ITU-T G.993.2].

         A special value (enum inactive) indicates that this
         counter is not active on the line. This occurs when the
         feature 'sos' is not supported.";
      reference
        "ITU-T G.997.1 clause 7.2.1.7.1 Far-end successful SOS
         count (SOS-SUCCESS-FE)";
    }
    leaf leftr-defects-seconds-counter-lfe {
      type bbf-yang:performance-counter32;
      description
        "Far-end line Low Error-Free Throughput (LEFTR) defects
         seconds counter. If retransmission is used in a given
         transmit direction, this parameter is a count of the seconds
         with a far-end leftr defect present (see clause 11.4.1 of
         [ITU-T G.998.4] for the definition of this counter).
         The far-end counter is only defined for downstream.";
      reference
        "ITU-T G.997.1 clause 7.2.1.2.6 leftr defects seconds
         counter";
    }
    leaf error-free-bits-counter-lfe {
      type bbf-yang:performance-counter32;
      description
        "Far-end line error-free bits counter. If retransmission
         is used in a given transmit direction, this parameter is
         a count of the number of error-free bits passed over the
         Beta1 reference point, divided by 65536 = 2^16 (see
         clause 11.4.2 of [ITU-T G.998.4] for the definition of
         this counter).
         This far-end counter is only defined for downstream.";
      reference
        "ITU-T G.997.1 clause 7.2.1.2.7 Error-free bits counter";
    }
    leaf minimum-error-free-throughput-lfe {
      type bbf-yang:performance-counter32;
      units "bit/s";
      description
        "Far-end minimum error-free throughput (MINEFTR). If
         retransmission is used in a given transmit direction,
         this parameter MINEFTR reports the minimum of the EFTR
         observed over the 15-min or 24-hour accumulation period
         (see clause 11.4.3 of [ITU-T G.998.4] for the definition
         of this parameter). The value is reported in bit/s.
         This far-end value is only defined for downstream.";
      reference
        "ITU-T G.997.1 clause 7.2.1.2.8 Minimum error-free
         throughput (MINEFTR)";
    }
    leaf loss-of-signal-fe {
      type bbf-yang:performance-counter32;
      description
        "Reports a count of the far-end Loss of Signal (LOS)
         failures.";
      reference
        "Borrowed from ITU-T G.997.2 clause 7.7.4 (LOS).
         Count of failures defined in ITU-T G.997.1
         clause 7.1.1.2.1.";
    }
    leaf loss-of-frame-fe {
      type bbf-yang:performance-counter32;
      description
        "Reports a count of the Loss of Frame (LOF) failures.";
      reference
        "Count of failures defined in ITU-T G.997.1
         clause 7.1.1.2.2.";
    }
    leaf loss-of-power-fe {
      type bbf-yang:performance-counter32;
      description
        "reports a count of the Loss of Power (LPR) failures.";
      reference
        "Borrowed from ITU-T G.997.2 clause 7.7.7 (LPR).
         Count of failures defined in ITU-T G.997.1
         clause 7.1.1.2.3.";
    }
    leaf maximum-error-free-throughput-lfe {
      if-feature "maxeftr";
      type bbf-yang:performance-counter32;
      units "bit/s";
      description
        "Far-end maximum error-free throughput (MAXEFTR). If
         retransmission is used in a given transmit direction,
         this parameter MAXEFTR reports the maximum of the EFTR
         observed over the 15-min or 24-hour accumulation period
         (see clause 11.4.4 of [ITU-T G.998.4] for the definition
         of this parameter). The value is reported in bit/s.
         This far-end value is only defined for downstream.";
      reference
        "ITU-T G.997.1 clause 7.2.1.2.9 Maximum error-free
         throughput (MAXEFTR)";
    }
    leaf sra-success-fe {
      if-feature "successful-sra";
      type bbf-yang:performance-counter32;
      description
        "This parameter is a count of the total number of
         successful Seamless Rate Adaptation (SRA) procedures
         initiated by the far-end xDSL Transceiver Unit (xTU) on the 
         line during the accumulation period. Parameter procedures 
         will be as defined in ITU-T G.997.1 clause 7.2.9. Successful 
         SRA is defined in clause 11.3.1.7 of [ITU-T G.993.2].";
      reference
        "ITU-T G.997.1 clause 7.2.9 Far-end successful SRA
         count (SRA-SUCCESS-FE)";
    }
  }

  // end grouping xtu-r-line-performance  

  grouping line-time-stamp {
    description
      "Time stamp for line performance parameters.";
    leaf time-stamp {
      type yang:date-and-time;
      description
        "Reports the start date/time for this interval.";
      reference
        "ITU-T G.997.2 clause 7.7.3.";
    }
  }
}
