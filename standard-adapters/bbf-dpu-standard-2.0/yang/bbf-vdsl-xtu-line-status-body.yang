submodule bbf-vdsl-xtu-line-status-body {
  yang-version 1.1;
  belongs-to bbf-vdsl {
    prefix bbf-vdsl;
  }

  import ietf-yang-types {
    prefix yang;
  }
  import bbf-yang-types {
    prefix bbf-yang;
  }
  include bbf-vdsl-base-body;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing Broadband Forum TR-252i3 clause 6.1 xDSL Transceiver 
     Unit (xTU) Line Status.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef time-stamp-or-undefined {
    type union {
      type enumeration {
        enum undefined {
          description
            "The value of the time stamp is undefined or unknown.";
        }
      }
      type yang:date-and-time;
    }
    description
      "The date/time associated with a particular time stamp. The
       special value, 'undefined', is used when the event represented
       by the time stamp has not yet occurred.";
  }

  grouping xtu-c-line-failure-parameters {
    description
      "xDSL Transceiver Unit - Central office (xTU-C) failure 
       parameters.";
    // xTU Current Status (Near-End Failures for xTU-C,
    // Far-End Failures for xTU-R) in BBF TR-252i3
    // encompasses los, lof, lpr, and linit
    leaf los {
      type boolean;
      description
        "A Loss of Signal (LOS) failure is declared after 2.5 +- 0.5 s
         of contiguous LOS defect, or, if LOS defect is present when
         the criteria for Loss of Frame (LOF) failure declaration have
         been met (see LOF definition below). A LOS failure is cleared
         after 10 +- 0.5 s of no LOS defect.";
      reference
        "ITU-T G.997.1 clause 7.1.1.1.1 Loss-of-signal (LOS)
         failure";
    }
    leaf lof {
      type boolean;
      description
        "A Loss of Frame (LOF) failure is declared after 2.5 +- 0.5 s
         of contiguous Severly Errored Frame (SEF) defect, except when
         an LOS defect or failure is present (see LOS definition
         above). A LOF failure is cleared when LOS failure is
         declared, or after 10 +- 0.5 s of no SEF defect.";
      reference
        "ITU-T G.997.1 clause 7.1.1.1.2 Loss-of-frame (LOF)
         failure";
    }
    leaf lpr {
      type boolean;
      description
        "A Loss of Power (LPR) failure is declared after 2.5 +- 0.5 s
         of contiguous near-end LPR primitive presence. An LPR
         failure is cleared after 10 +- 0.5 s of no near-end LPR
         primitive presence.";
      reference
        "ITU-T G.997.1 clause 7.1.1.1.3 Loss-of-power (LPR)
         failure";
    }
    leaf linit {
      type boolean;
      description
        "If the line is forced to the L0 state (or into loop
         diagnostic mode) and an attempt to reach the L0 state
         (or to successfully complete the loop diagnostic
         procedures) fails (after a vendor discretionary number
         of retries and/or within a vendor discretionary
         timeout), then an initialization failure occurs. An
         initialization failure cause and last successful
         transmitted state are given by the line initialization
         (LINIT) failure (see clause 7.5.1.6). A line initialization
         failure will be conveyed to the NMS by the xDSL Transceiver 
         Unit - Central office (xTU-C) (over the Q-interface) and 
         should be conveyed to the NMS by the xDSL Transceiver Unit - 
         Remote side (xTU-R) (over the T-/S-interface) after it is
         detected.";
      reference
        "ITU-T G.997.1 clause 7.1.1.3 Line initialization (LINIT)
         failure";
    }
    leaf loss-of-margin {
      type boolean;
      description
        "A Loss of Margin (LOM) failure is declared when a
         re-initialization is triggered by a persistent near-end
         lom defect, except when an Loss of Signal (LOS) or Loss of
         Frame (LOF) defect or failure is present (see los and lof
         definitions above). A LOM failure is cleared when LOS or LOF
         failure is declared, or after 10 +- 0.5 seconds of no LOM
         defect.";
      reference
        "ITU-T G.997.1 clause 7.1.1.1.4 Loss of margin (LOM)
         failure";
    }
  }

  // end grouping xtu-c-line-failure-parameters

  grouping xtu-r-line-failure-parameters {
    description
      "xDSL Transceiver Unit - Remote side (xTU-R) line failure 
       parameters.";
    // Far-End Failures for xTU-R) in BBF TR-252i3
    // encompasses los-fe, lof-fe, lpr-fe, and linit
    leaf los-fe {
      type boolean;
      description
        "A Far-End Loss of Signal (LOS-FE) failure is declared
         after 2.5 +- 0.5 s of contiguous far-end Loss of Signal (LOS)
         defects, or, if far-end LOS defect is present when the
         criteria for Loss of Frame (LOF) failure declaration have
         been met (see LOF definition below). A far-end LOS failure is
         cleared after 10 +- 0.5 s of no far-end LOS defect.";
      reference
        "ITU-T G.997.1 clause 7.1.1.2.1 Far-end loss-of-signal
         (LOS-FE) failure";
    }
    leaf lof-fe {
      type boolean;
      description
        "A Far-End Loss of Frame (LOF-FE) failure is declared
         after 2.5 +- 0.5 s of contiguous Remote Defect Indication
         (RDI) defects, except when a far-end Loss of Signal (LOS)
         defect or failure is present (see LOS definition above). A
         far-end Loss of Frame (LOF) failure is cleared when far-end
         LOS failure is declared, or after 10 +- 0.5 s of no RDI
         defect.";
      reference
        "ITU-T G.997.1 clause 7.1.1.2.2 Far-end loss-of-frame
         (LOF-FE) failure";
    }
    leaf lpr-fe {
      type boolean;
      description
        "A Far-End Loss of Power (LPR-FE) failure is declared
         after the occurrence of a far-end LPR primitive followed
         by 2.5 +- 0.5 s of contiguous near-end Loss of Signal (LOS)
         defects. A far-end LPR failure is cleared after 10 +- 0.5 s
         of no near-end LOS defect.";
      reference
        "ITU-T G.997.1 clause 7.1.1.2.3 Far-end loss-of-power
         (LPR-FE) failure";
    }
    leaf loss-of-margin-fe {
      type boolean;
      description
        "A Far-End Loss of Margin (LOM-FE) failure is declared
         when a re-initialization is triggered by a persistent
         far-end lom defect, except when an Far-End Loss of Signal
         (LOS-FE) or Far-End Loss of Frame (LOF-FE) defect or failure
         is present (see los-fe and lof-fe definitions above). A far
         end LOM failure is cleared when far end LOS or LOF failure is
         declared, or after 10 +- 0.5 s of no far end LOM defect.";
      reference
        "ITU-T G.997.1 clause 7.1.1.2.4 Loss of margin (LOM-FE)
         failure";
    }
  }

  // end grouping xtu-r-line-failure-parameters

  grouping xtu-line-status {
    description
      "Status parameters for the line.";
    leaf snr-margin {
      type union {
        type int16 {
          range "-640..630";
        }
        type enumeration {
          enum out-of-range {
            description
              "Indicates that the value is out of range to
               be represented.";
          }
        }
      }
      units "0.1 dB";
      status obsolete;
      description
        "The signal-to-noise ratio (SNR) margin is the maximum
         increase, in dB, of the noise power received at the
         receiver, such that the Bit Error Rate (BER) requirements are
         met for all bearer channels (SNRMds for xDSL Transceiver 
         Unit - Remote side (xTU-R) / SNRMus for xDSL Transceiver 
         Unit - Central office (xTU-C)). The SNR margin ranges from 
         -64 dB to +63 dB, with 0.1 dB steps. A special value (enum 
         out-of-range) indicates the parameter is out of range to be 
         represented.";
      reference
        "ITU-T G.997.1 clause 7.5.1.13 Downstream signal-to-noise
         ratio margin (SNRMds) and 7.5.1.16 Upstream
         signal-to-noise ratio margin (SNRMus";
    }
    leaf profile {
      type profiles;
      description
        "This parameter defines the profile in use. It is coded
         in a bit-map representation with the bits using the
         definition in ITU-T G997.1 clause 7.3.1.1.11 (0 if in
         use, 1 if not in use).";
      reference
        "ITU-T G.997.1 clause 7.5.1.2 VDSL2 profile";
    }
    leaf limitmask {
      type limitmask-descriptor;
      // limitmask-descriptor is defined in bbf-vdsl-base-body.yang
      description
        "This configuration parameter contains the G.993.2 limit
         PSD masks of the selected Power Spectral Density (PSD) mask
         class, that is used by the near-end xDSL Transceiver Unit 
         (xTU) on this line. One LIMITMASK parameter is defined per 
         the G.993.2 Annex.";
      reference
        "ITU-T G.997.1 clause 7.5.1.3 VDSL2 limit PSD mask and
         band plan.";
    }
    leaf us0mask {
      type us0mask-descriptor;
      // us0mask-descriptor is defined in bbf-vdsl-base-body.yang
      description
        "This parameter contains none or the one US0 Power Spectral
         Density (PSD) masks in use by the near-end xDSL Transceiver 
         Unit (xTU) on the line.";
      reference
        "ITU-T G.997.1 clause 7.5.1.4 VDSL2 US0 PSD mask.";
    }
    leaf actual-cyclic-extension {
      type uint8 {
        range "2..16";
      }
      units "N/32 samples, where 2N is the IDFT size";
      description
        "This parameter reports the cyclic extension used on the
         line. It is coded as an unsigned integer from 2 to 16 in
         units of N/32 samples, where 2N is the IDFT size.";
      reference
        "ITU-T G.997.1 clause 7.5.1.32 Actual cyclic extension
         (ACTUALCE)";
    }
    leaf actual-aele-mode {
      type enumeration {
        enum 0 {
          description
            "kl0[band] = ELE-M0 VDSL Transceiver Unit - central Office
             (VTU-O) kl0 estimate.";
        }
        enum 1 {
          description
            "kl0[band] = ELEDS [dB], with band in the set
             {upbo_bands}.";
        }
        enum 2 {
          description
            "kl0[band] = ELE[band] [dB], with band in the set
             {upbo_bands}.";
        }
        enum 3 {
          description
            "kl0[band] = MIN(ELEUS, ELEDS) [dB], with band in the
             set {upbo_bands}.";
        }
      }
      description
        "This parameter reports the actual Alternative Electrical
         Length Estimation Mode (AELE-MODE) used in
         clause 7.2.1.3.2.1 of [ITU-T G.993.2]. The value of this
         parameter is 0, 1, 2 or 3.";
      reference
        "ITU-T G.997.1 clause 7.5.1.23.7 Actual Alternative
         Electrical Length Estimation Mode (ACT-AELE-MODE)";
    }
    leaf actual-vector-mode {
      type enumeration {
        enum 0 {
          description
            "If Actual Vector Mode (ACTVECTORMODE) equals 0, the line
             is initialized in G.993.2 mode different from Annex X or
             Annex Y.";
        }
        enum 1 {
          description
            "If Actual Vector Mode (ACTVECTORMODE) equals 1, the line
             is initialized in G.993.2 Annex X.";
        }
        enum 2 {
          description
            "If Actual Vector Mode (ACTVECTORMODE) equals 2, the line
             is initialized in G.993.2 Annex Y.";
        }
        enum 3 {
          description
            "If Actual Vector Mode (ACTVECTORMODE) equals 3, the line
             is initialized in G.993.5.";
        }
      }
      description
        "This parameter reports the vectoring initialization type
         of the line.";
      reference
        "ITU-T G.997.1 clause 7.5.1.43.1 Actual vectoring mode
         (ACTVECTORMODE)";
    }
    leaf attndr-actual-method {
      type uint8 {
        range "0..2";
      }
      description
        "This parameter indicates the actual Attainable Net Data Rate
         (ATTNDR) Method used for calculation of the ATTNDR in the
         downstream and upstream direction. For detailed definition
         see G.993.2 clause 11.4.1.1.7.";
      reference
        "ITU-T G.997.1 clause 7.5.1.41.1 ATTNDR Actual Method
         (ATTNDR_ACTMETHOD)";
    }
  }

  // end grouping xtu-line-status
  // Begin directional grouping for receiver 
  // upstream/downstream uses

  grouping xtu-line-status-receiver-directional {
    description
      "Directional line status for receiver.";
    leaf actual-snr-mode {
      type enumeration {
        enum 1 {
          description
            "If the Actual Signal-to-Noise Ratio Mode (ACTSNRMODE)
             equals 1, the virtual noise is inactive.";
        }
        enum 2 {
          description
            "For downstream, if the Actual Signal-to-Noise Ratio Mode
             (ACTSNRMODE) equals 2, the virtual noise is active.
             For upstream, if ACTSNRMODE equals 2,
             the transmitter-referred virtual noise is active.";
        }
        enum 3 {
          description
            "For upstream, if the Actual Signal-to-Noise Ratio Mode
             (ACTSNRMODE) equals 3, the receiver-referred virtual
             noise is active.";
        }
        enum 4 {
          description
            "For downstream, If the Actual Signal-to-Noise Ratio Mode
             (ACTSNRMODE) equals 4, the virtual noise together with
             the virtual noise scaling factor is active.
             For upstream, if ACTSNRMODE equals 4, the receiver-
             referred virtual noise together with the virtual noise
             scaling factor is active.";
        }
      }
      description
        "This parameter indicates if the transmitter referred
         virtual noise is active on the line in the direction
         toward the receiver (ACTSNRMODEds for xDSL Transceiver 
         Unit - Remote side (xTU-R) / ACTSNRMODEus for xDSL 
         Transceiver Unit - Central office (xTU-C)).";
      reference
        "ITU-T G.997.1 clause 7.5.1.15 Actual downstream
         signal-to-noise ratio mode (ACTSNRMODEds) and clause
         7.5.1.18 Actual upstream signal-to-noise ratio mode
         (ACTSNRMODEus)";
    }
    leaf attainable-net-data-rate {
      type bbf-yang:data-rate32-or-undetermined;
      description
        "This parameter indicates the maximum net data rate
         currently attainable from the transmitter (ATTNDRds for
         xDSL Transceiver Unit - Central office (xTU-C) / ATTNDRus for
         xDSL Transceiver Unit - Remote side (xTU-R)). The rate is 
         coded in steps of 1,000 bit/s.";
      reference
        "ITU-T G.997.1 clause 7.5.1.19 Downstream maximum
         attainable data rate (ATTNDRds) and clause 7.5.1.20
         Upstream maximum attainable data rate (ATTNDRus)";
    }
    leaf trellis {
      type boolean;
      description
        "This parameter reports whether trellis coding is in
         use in the direction of transmission. It is
         represented as one bit coded as 0 (false) if the
         trellis is not used and as 1 (true) if the trellis is
         used.";
      reference
        "ITU-T G.997.1 clause 7.5.1.30 Downstream trellis use
         (TRELLISds) and clause 7.5.1.31 Upstream trellis use
         (TRELLISus)";
    }
    leaf actual-ra-mode {
      type enumeration {
        enum 1 {
          description
            "If the Actual Rate Adaptation Mode (ACT-RA-MODE) equals
             1, the link is operating in RA-MODE 1 (MANUAL).";
        }
        enum 2 {
          description
            "If the Actual Rate Adaptation Mode (ACT-RA-MODE) equals
             2, the link is operating in RA-MODE 2 (AT_INIT).";
        }
        enum 3 {
          description
            "If the Actual Rate Adaptation Mode (ACT-RA-MODE) equals
             3, the link is operating in RA-MODE 3 (DYNAMIC).";
        }
        enum 4 {
          description
            "If the Actual Rate Adaptation Mode (ACT-RA-MODE) equals
             4, the link is operating in RA-MODE 4 (DYNAMIC with
             SOS).";
        }
      }
      description
        "This parameter indicates the actual active Rate Adatpation
         Mode (RA-MODE) in the direction of transmission.";
      reference
        "ITU-T G.997.1 clause 7.5.1.33.1 Actual downstream rate
         adaptation mode (ACT-RA-MODEds) and clause 7.5.1.33.2
         Actual upstream rate adaptation mode (ACT-RA-MODEus)";
    }
    leaf rxthrh {
      type uint8 {
        range "36..100";
      }
      units "1 dB";
      description
        "This parameter reports the received signal level
         threshold (RXTHRH) value used in the alternative electrical
         length estimation method (ELE-M1) in ITU-T G.997.1
         clause 7.2.1.3.2.2 in the direction of transmission.
         This parameter represents an offset from -100 dBm/Hz,
         and ranges from -64 dB to 0 dB in steps of 1 dB.";
      reference
        "ITU-T G.997.1 clause 7.5.1.23.5 UPBO downstream
         receiver signal level threshold (RXThrHds) and clause
         7.5.1.23.6 UPBO upstream receiver signal level
         threshold (RXThrHus)";
    }
    leaf actual-inp-roc {
      type uint8 {
        range "0..254 | 255";
      }
      units "0.1 T4k periods";
      description
        "This parameter reports the Actual Impulse Noise Protection
         (ACTINP) of the Robust Overhead Channel (ROC) in the
         direction of transmission. The format and usage is identical
         to the channel status parameter ACTINP (see ITU-T G997.1
         clause 7.5.2.4).

         A special value (255) is used to indicate the ACTINP is
         greater than 25.4 T4k periods where a T4k period is about
         250 microseconds.";
      reference
        "ITU-T G.997.1 clause 7.5.1.34.1 Downstream actual
         impulse noise protection of ROC (ACTINP-ROC-ds) and
         clause 7.5.1.34.2 Upstream actual impulse noise
         protection of ROC (ACTINP-ROC-us)";
    }
    leaf snr-margin-roc {
      type union {
        type int16 {
          range "-640..630";
        }
        type enumeration {
          enum out-of-range {
            description
              "Indicates that the value is out of range to
               be represented.";
          }
        }
      }
      units "0.1 dB";
      description
        "This parameter reports the actual signal-to-noise
         margin of the Robust Overhead Channel (ROC) in the direction
         of transmission.
         The format is identical to the format of the line
         status parameter Signal-to-Noise Ration Margin (SNRM) (see
         ITU-T G997.1 clause 7.5.1.13). The SNRM-ROC ranges from -64
         dB to +63 dB, with 0.1 dB steps. A special value (enum
         out-of-range) indicates the parameter is out of range to be
         represented.";
      reference
        "ITU-T G.997.1 clause 7.5.1.35.1 Downstream actual SNR
         margin of ROC (SNRM-ROC-ds) and clause 7.5.1.35.2
         Upstream actual SNR margin of ROC (SNRM-ROC-us)";
    }
    leaf stamp-olr {
      type time-stamp-or-undefined;
      description
        "This parameter indicates the date/time of the last
         successful On-Line Reconfiguration (OLR) execution in the
         direction of transmission that has modified the bits or
         gains. This date/time-stamp will include information on the
         Year, Month, Day, Hour, Minute and Second of the last OLR.";
      reference
        "ITU-T G.997.1 clause 7.5.1.37.1 Date/time-stamping of
         last successful downstream OLR operation
         (STAMP-OLR-ds) and Clause 7.5.1.37.2 Date/time-stamping
         of last successful upstream OLR operation
         (STAMP-OLR-us)";
    }
    leaf actual-ripolicy {
      type enumeration {
        enum 0 {
          description
            "Re-Initialization Policy (RIPOLICY) 0.";
        }
        enum 1 {
          description
            "Re-Initialization Policy (RIPOLICY) 1.";
        }
      }
      description
        "This parameter indicates the actual Re-Initialization Policy
         (RIPOLICY) in use in the direction of transmission.";
      reference
        "ITU-T G.997.1 clause 7.5.1.40.1 Actual downstream
         RIPOLICY (ACTRIPOLICYds) and clause 7.5.1.40.2 Actual
         upstream RIPOLICY (ACTRIPOLICYus)";
    }
    leaf rtx-used {
      type enumeration {
        enum 1 {
          description
            "Retransmission (RTX) in use.";
        }
        enum 2 {
          description
            "Retransmission (RTX) not in use, due to RTX_MODE =
             FORBIDDEN.";
        }
        enum 3 {
          description
            "Retransmission (RTX) not in use, due to not supported by
             the XTU-C.";
        }
        enum 4 {
          description
            "Retransmission (RTX) not in use, due to not supported by
             the XTU-R.";
        }
        enum 5 {
          description
            "Retransmission (RTX) not in use, due to not supported by
             the XTU-C and XTU-R.";
        }
      }
      description
        "This parameter specifies whether ITU-T G.998.4
         Retransmission (RTX) is used (i.e., active in showtime) in a
         given transmit direction. In [ITU-T G.992.3] and
         [ITU-T G.992.5] only the downstream parameter RTX_USED
         is relevant and the value in the upstream direction is
         ignored. In [ITU-T G.993.2], both parameters are
         relevant.";
      reference
        "ITU-T G.997.1 clause 7.5.1.38 Retransmission used
         (RTX_USED)";
    }
    leaf attndr-actual-inp {
      type uint16 {
        range "0..2046 | 2047";
      }
      units "0.1 DMT symbols";
      description
        "If retransmission is not used in the direction of
         transmission, this parameter indicates the actual
         impulse noise protection used in the improved
         calculation of the Attainable Net Data Rate (ATTNDR) in the
         direction of transmission.
         If retransmission is used in the direction of
         transmission, this parameter indicates the actual
         impulse noise protection against Single High Impulse Noise
         Event (SHINE) used in the improved calculation of the ATTNDR
         in the direction of transmission.
         The value is coded in fractions of Discrete Multi-Tone (DMT)
         symbols with a granularity of 0.1 symbols. The range is from
         0 to 204.6. A special value of 2047 indicates an Actual
         Impulse Noise Protection (ACTINP) of 204.7 or higher.";
      reference
        "ITU-T G.997.1 clause 7.5.1.41.2 ATTNDR Downstream
         Actual impulse noise protection (ATTNDR_ACTINPds) and
         clause 7.5.1.41.3 ATTNDR Upstream Actual impulse noise
         protection (ATTNDR_ACTINPus)";
    }
    leaf attndr-actual-inp-rein {
      type uint8 {
        range "0..254 | 255";
      }
      units "0.1 DMT symbols";
      description
        "If retransmission is used in the direction of
         transmission, this parameter reports the actual
         impulse noise protection (INP) against Repetitive Electrical
         Impulse Noise (REIN) used in the improved calculation of the
         Attainable Net Data Rate (ATTNDR) in the direction of
         transmission.
         The value is coded in fractions of Discrete Multi-Tone (DMT)
         symbols with a granularity of 0.1 symbols. The value is coded
         in fractions of DMT symbols with a granularity of 0.1
         symbols. The range is from 0 to 25.4. A special value
         of 255 indicates an ATTNDR_ACTINP_REIN of 25.5 or
         higher.";
      reference
        "ITU-T G.997.1 clause 7.5.1.41.4 ATTNDR Downstream
         Actual impulse noise protection against REIN
         (ATTNDR_ACTINP_REINds and clause 7.5.1.41.5 ATTNDR
         Upstream Actual impulse noise protection against REIN
         (ATTNDR_ACTINP_REINus)";
    }
    leaf attndr-actual-delay {
      type uint8 {
        range "0..254 | 255";
      }
      units "0.1 milliseconds";
      description
        "This parameter indicates the actual delay used in the
         improved calculation of the Attainable Net Data Rate (ATTNDR)
         in the direction of transmission. The value is coded in with
         a granularity of 0.1 ms. The range is from 0 to 25.4 ms. A
         special value of 255 indicates an actual delay of 25.5 ms or
         higher.";
      reference
        "ITU-T G.997.1 clause 7.5.1.41.6 ATTNDR Downstream
         Actual delay (ATTNDR_ACTDELAYds) and clause 7.5.1.41.7
         ATTNDR Upstream Actual delay (ATTNDR_ACTDELAYus)";
    }
    leaf snr-margin {
      type union {
        type int16 {
          range "-640..630";
        }
        type enumeration {
          enum out-of-range {
            description
              "Indicates that the value is out of range to
               be represented.";
          }
        }
      }
      units "0.1 dB";
      description
        "The Signal-to-Noise Ratio (SNR) margin is the maximum
         increase, in dB, of the noise power received at the
         receiver, such that the Bit Error Rate (BER) requirements are
         met for all bearer channels (SNRMds for xDSL Transceiver 
         Unit - Remote side (xTU-R) / SNRMus for xDSL Transceiver 
         Unit - Central office (xTU-C)). The SNR margin ranges from 
         -64 dB to +63 dB, with 0.1 dB steps. A special value (enum 
         out-of-range) indicates the parameter is out of range to be 
         represented.";
      reference
        "ITU-T G.997.1 clause 7.5.1.13 Downstream signal-to-noise
         ratio margin (SNRMds) and 7.5.1.16 Upstream
         signal-to-noise ratio margin (SNRMus";
    }
  }

  // end grouping xtu-line-status-receiver-directional
  // Begin directional grouping for transmitter 
  // upstream/downstream uses

  grouping xtu-line-status-transmitter-directional {
    description
      "Directional line status for transmitter.";
    leaf last-transmitted-state {
      type uint8;
      description
        "This parameter represents the last successful
         transmitted initialization state known by the
         transmitter in the last full initialization performed on
         the line (Downstream for xDSL Transceiver Unit - Central 
         office (xTU-C) / Upstream for xDSL Transceiver Unit - Remote 
         side (xTU-R)). Initialization states are defined in the 
         individual xDSL Recommendations and are counted from 0 (if 
         [ITU-T G.994.1] is used) or 1 (if [ITU-T G.994.1] is not 
         used) up to showtime. This parameter will be interpreted 
         along with the xDSL transmission system.
         This parameter is available only when, after a failed
         full initialization, the loop diagnostic procedures are
         activated on the line. Loop diagnostic procedures can be
         activated by the operator of the system (through the
         line state forced line configuration parameter) or
         autonomously by the xTU-C or xTU-R.";
      reference
        "ITU-T G.997.1 clause 7.5.1.7 Downstream last transmitted
         state and clause 7.5.1.8 Upstream last transmitted
         state";
    }
    leaf actual-psd {
      type union {
        type int16 {
          range "-900..0";
        }
        type enumeration {
          enum out-of-range {
            description
              "Indicates that the parameter is out of range to
               be represented.";
          }
        }
      }
      units "0.1 dB";
      description
        "This parameter is the average transmit Power Spectral Density
         (PSD) over the used subcarriers (subcarriers to which user
         data are allocated) delivered by the xDSL Transceiver 
         Unit - Central office (xTU-C) at the U-C reference point 
         (ACTPSDds), or delivered by the xDSL Transceiver 
         Unit - Remote side (xTU-R) at the U-R reference point 
         (ACTPSDus), at the instant of measurement. The PSD level 
         ranges from -90 dBm/Hz to 0 dBm/Hz, with 0.1 dB steps. A 
         special value (enum out-of-range) indicates the parameter is 
         out of range to be represented. See Clause 8.5.1 of
         [ITU-T G.992.3].";
      reference
        "ITU-T G.997.1 clause 7.5.1.21 Downstream actual power
         spectral density (ACTPSDds) and clause 7.5.1.22 Upstream
         actual power spectral density (ACTPSDus)";
    }
    leaf actual-aggregate-transmit-power {
      type union {
        type int16 {
          range "-310..310";
        }
        type enumeration {
          enum out-of-range {
            description
              "Indicates that the parameter is out of range to
               be represented.";
          }
        }
      }
      units "0.1 dB";
      description
        "This parameter is the total amount of transmit power
         delivered by the xDSL Transceiver Unit - Central office 
         (xTU-C) at the U-C reference point (ACTPSDds), or by the xDSL
         Transceiver Unit - Remote side (xTU-R) at the U-R reference 
         point (ACTPSDus), at the instant of measurement. The total
         output power level ranges from -31 dBm to +31 dBm, with
         0.1 dB steps. A special value (enum out-of-range) indicates
         the parameter is out of range to be represented.
         See clause 8.12.3.8 of [ITU-T G.992.3] and
         clause 10.3.4.2.1 of [ITU-T G.993.2].";
      reference
        "ITU-T G.997.1 clause 7.5.1.24 Downstream actual
         aggregate transmit power (ACTATPds) and clause 7.5.1.25
         Upstream actual aggregate transmit power (ACTATPus)";
    }
    leaf aggachndr {
      type bbf-yang:data-rate32-or-undetermined;
      description
        "This parameter reports the aggregate achievable net data
         rate of the (Near-end) VDSL Transceiver Unit - central Office
         (VTU-O) or (Far-end) VDSL Transceiver Unit - Remote side 
         (VTU-R) as specified in G.998.4. The value is coded in step 
         of 1000 bit/s. A special value indicates that the aggregate
         achievable net data rate value is reported as being
         undetermined.";
      reference
        "ITU-T G.997.1 clause 7.5.1.42.1 Near-end Aggregate
         achievable net data rate (AGGACHNDR_NE) and clause
         7.5.1.42.2 Far-end Aggregate achievable net data rate
         (AGGACHNDR_FE)";
    }
  }

  // end grouping xtu-line-status-transmitter-directional
  // Now xtu-c and xtu-r containers defined here

  grouping xtu-c-status {
    description
      "xDSL Transceiver Unit - Central office (xTU-C) line status. 
       This represents transmission in the upstream direction.";
    leaf stamp-test-ne {
      type time-stamp-or-undefined;
      description
        "This parameter is defined in the Access Node Management
         Information Base (AN MIB) and indicates the date/time when
         the near-end test parameters that can change during showtime
         were last updated. This date/time-stamp will include
         information on the Year, Month, Day, Hour, Minute and Second
         of the last update.";
      reference
        "ITU-T G.997.1 clause 7.5.1.36.3 Date/time-stamping of
         near-end test parameters (STAMP-TEST-NE)";
    }
    container failures {
      description
        "xDSL Transceiver Unit - Central office (xTU-C) line 
         failures.";
      uses xtu-c-line-failure-parameters;
    }
    container downstream {
      description
        "Downstream xDSL Transceiver Unit (xTU) status.";
      uses xtu-line-status-transmitter-directional;
    }
    container upstream {
      description
        "Upstream xDSL Transceiver Unit (xTU) status.";
      uses xtu-line-status-receiver-directional;
    }
  }

  // end xtu-c-status

  grouping xtu-r-status {
    description
      "xDSL Transceiver Unit - Remote side (xTU-R) line status. This 
       represents transmission in the downstream direction.";
    leaf stamp-test-fe {
      type time-stamp-or-undefined;
      description
        "This parameter is defined in the Access Node Management
         Information Base (AN MIB) and indicates the date/time when
         the far-end test parameters that can change during showtime
         were last updated. This date/time-stamp will include
         information on the Year, Month, Day, Hour, Minute and Second
         of the last update.";
      reference
        "ITU-T G.997.1 clause 7.5.1.36.4 Date/time-stamping of
         far-end test parameters (STAMP-TEST-FE)";
    }
    container failures {
      description
        "xDSL Transceiver Unit - Remote side (xTU-R) line failures.";
      uses xtu-r-line-failure-parameters;
    }
    container downstream {
      description
        "Downstream xDSL Transceiver Unit (xTU) status.";
      uses xtu-line-status-receiver-directional;
    }
    container upstream {
      description
        "Upstream xDSL Transceiver Unit (xTU) status.";
      uses xtu-line-status-transmitter-directional;
    }
  }

  // end xtu-r-status
}
