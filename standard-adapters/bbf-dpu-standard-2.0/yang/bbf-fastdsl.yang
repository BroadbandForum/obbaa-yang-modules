module bbf-fastdsl {
  yang-version 1.1;
  namespace "urn:bbf:yang:bbf-fastdsl";
  prefix bbf-fastdsl;

  import ietf-interfaces {
    prefix if;
  }
  import iana-if-type {
    prefix ianaift;
  }
  import bbf-availability {
    prefix bbf-avail;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";
  description
    "This module contains a collection of YANG definitions for 
     supporting the Broadband Forum requirements on management of 
     interfaces which support one or more DSL or G.fast technologies. 
     As such, this module is specific to access network equipment 
     (e.g., BBF-specified Access Nodes and FTTdp DPUs).

     Copyright (c) 2016-2019 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a2; see
     the TR itself for full legal notices.";

  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  identity fastdsl-mode {
    description
      "Base identity for FastDSL modes.";
  }

  identity mode-fast {
    base fastdsl-mode;
    description
      "ITU-T G.9701 G.fast.";
  }

  identity mode-vdsl {
    base fastdsl-mode;
    description
      "ITU-T G.993.2 VDSL2 or derived technology.";
  }

  identity configured-mode-fast-not-supported {
    base bbf-avail:issue-tag;
    description
      "The configured mode, 'mode-fast' of the FastDSL line is not
       supported.";
  }

  identity configured-mode-vdsl-not-supported {
    base bbf-avail:issue-tag;
    description
      "The configured mode, 'mode-vdsl' of the FastDSL line is not
       supported.";
  }

  typedef fastdsl-mode-ref {
    type identityref {
      base fastdsl-mode;
    }
    description
      "Reference to a FastDSL mode of operation.";
  }

  augment "/if:interfaces/if:interface" {
    when "if:type = 'ianaift:fastdsl'" {
      description
        "Only applicable when the interface type is 'fastdsl'.";
    }
    description
      "Data nodes for the configuration of FastDSL lines.";
    container line {
      presence
        "If present, indicates that the interface is able to operate
         according to the appropriate ITU-T specification for one
         or more DSL or G.fast technologies.";
      description
        "Line configuration data for FastDSL interfaces.";
      leaf-list supported-mode {
        type fastdsl-mode-ref;
        config false;
        status deprecated;
        description
          "Supported mode(s) of operation.";
      }
      leaf-list configured-mode {
        type fastdsl-mode-ref;
        description
          "Configured mode(s) of operation. If no elements exist, the
           configured mode is undetermined.";
      }
    }
  }

  augment "/if:interfaces-state/if:interface" {
    when "if:type = 'ianaift:fastdsl'" {
      description
        "Only applicable when the interface type is 'fastdsl'.";
    }
    description
      "Data nodes for the operational state of FastDSL lines.";
    container line {
      presence
        "If present, indicates that the interface is able to operate
         according to the appropriate ITU-T specification for one
         or more DSL or G.fast technologies.";
      description
        "Line state data for FAST interfaces.";
      leaf operational-mode {
        type union {
          type enumeration {
            enum undetermined {
              description
                "The current mode of operation is undetermined. This
                 is most likely due to the fact that G.hs has not
                 completed the first time.";
            }
          }
          type fastdsl-mode-ref;
        }
        description
          "Current mode of operation. Upon initialization, the mode
           will be undetermined until G.hs successfully completes
           for the first time.";
      }
    }
  }
}
