module bbf-fast {
  yang-version 1.1;
  namespace "urn:bbf:yang:bbf-fast";
  prefix bbf-fast;

  /* Common */

  include bbf-fast-base;
  include bbf-fast-pointers;
  include bbf-fast-perf-types;

  /* Quality Profiles */

  include bbf-fast-quality-profiles;
  include bbf-fast-fast-rate-adaptation-profile-body;
  include bbf-fast-noise-margin-profile-body;
  include bbf-fast-fast-retrain-policy-profile-body;
  include bbf-fast-retransmission-profile-body;
  include bbf-fast-vectoring-profile-body;
  include bbf-fast-impulse-noise-monitoring-profile-body;

  /* Service Profiles */

  include bbf-fast-service-profiles;
  include bbf-fast-data-rate-profile-body;

  /* Spectrum Profiles */

  include bbf-fast-spectrum-profiles;
  include bbf-fast-line-spectrum-profile-body;
  include bbf-fast-upstream-power-back-off-profile-body;
  include bbf-fast-rfi-profile-body;

  /* TDD Profiles */

  include bbf-fast-tdd-profiles;
  include bbf-fast-tdd-profile-body;

  /* Test Diagnostics */

  include bbf-fast-test-diagnostics;
  include bbf-fast-test-mode-body;
  include bbf-fast-update-test-body;
  include bbf-fast-link-state-body;
  include bbf-fast-read-test-body;

  /* Threshold Management */

  include bbf-fast-threshold-management;
  include bbf-fast-line-threshold-profile-body;
  include bbf-fast-channel-threshold-profile-body;
  include bbf-fast-threshold-crossing-alert-body;

  /* Performance Management */

  include bbf-fast-performance-management;
  include bbf-fast-line-performance-body;
  include bbf-fast-channel-performance-body;

  /* Status Monitoring */

  include bbf-fast-status-monitoring;
  include bbf-fast-line-status-body;
  include bbf-fast-channel-status-body;

  /* Inventory */

  include bbf-fast-inventory;
  include bbf-fast-ftu-inventory-body;

  /* Availability */

  include bbf-fast-availability;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This module contains a collection of YANG definitions for 
     supporting the Broadband Forum requirements on management of 
     FAST interfaces as defined in ITU-T G.9700, ITU-T G.9701, ITU-T 
     G.997.2 and BBF TR-371. As such, this module is specific to 
     access network equipment (e.g., BBF-specified Access Nodes and 
     FTTdp DPUs).

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }
}
