submodule bbf-fast-upstream-power-back-off-profile-body {
  yang-version 1.1;
  belongs-to bbf-fast {
    prefix bbf-fast;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing upstream power back off profiles.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping upstream-power-back-off-parameters {
    description
      "Power-back-off-specific configuration parameters.";
    reference
      "ITU-T G.997.2 clause 7.1.2.";
    leaf upbopsd-a {
      type uint16 {
        range "0..4095" {
          description
            "Defines a range equal to 40.00..80.95 dBm/Hz. Uses an
             offset of 40.00 dBm/Hz.";
        }
      }
      units "0.01 dBm/Hz";
      default "0";
      description
        "Defines the parameter a for the Upstream power back-off
         (UPBO) reference Power Spectral Density (PSD) used to
         compute the upstream power back-off for the upstream
         frequency band.";
      reference
        "ITU-T G.997.2 clause 7.1.2.9 (UPBOPSDA); ITU-T G.9701
         clause 7.3.1.4.";
    }
    leaf upbopsd-b {
      type uint16 {
        range "0..4095" {
          description
            "Defines a range equal to 0..40.95 dBm/Hz.";
        }
      }
      units "0.01 dBm/Hz";
      default "0";
      description
        "Defines the parameter b for the Upstream power back-off
         (UPBO) reference Power Spectral Density (PSD) used to
         compute the upstream power back-off for the upstream
         frequency band.";
      reference
        "ITU-T G.997.2 clause 7.1.2.10 (UPBOPSDB); ITU-T G.9701
         clause 7.3.1.4.";
    }
    leaf upbo-upstream-electrical-length {
      type uint16 {
        range "0..1280" {
          description
            "Defines a range equal to 0..128 dB.";
        }
      }
      units "0.1 dB";
      default "0";
      description
        "Defines the electrical length kl0 (expressed in dB at
         1 MHz).";
      reference
        "ITU-T G.997.2 clause 7.1.2.11 (UPBOKL); ITU-T G.9701 clause
         7.3.1.4.2.1.";
    }
    leaf upbo-force-electrical-length {
      type boolean;
      default "false";
      description
        "Defines whether or not the FAST Transceiver Unit - Remote 
         side (FTU-R) is forced to use the electrical length kl0 = 
         UPBOKL to compute the UPBOMASK. If not forced, the FAST 
         Transceiver Units (FTU) determine the electrical length 
         kl0.";
      reference
        "ITU-T G.997.2 clause 7.1.2.12 (UPBOKLF); ITU-T G.9701
         clause 7.3.1.4.2.1.";
    }
    leaf upbo-reference-electrical-length {
      type uint16 {
        range "0 | 18..255" {
          description
            "Defines a range equal to 1.8..25.5 dB.
             Special value 0: Use the Equal Power Spectral Density
             (PSD) Upstream power back-off (UPBO) method.";
        }
      }
      units "0.1 dB";
      default "0";
      description
        "Defines the Upstream power back-off (UPBO) reference
         electrical length kl0_REF used to compute the upstream power
         back-off for the Equalized Far-End Crosstalk (FEXT) Upstream
         power back-off (UPBO) method. If kl0_REF = 0 (special value)
         then the Equal Power Spectral Density (PSD) Upstream power
         back-off (UPBO) method is used.";
      reference
        "ITU-T G.997.2 clause 7.1.2.13 (UPBOKLREF); ITU-T G.9701
         clause 7.3.1.4.2.2.";
    }
  }

  grouping upstream-power-back-off-profile {
    description
      "Defines the parameters contained in an upstream power back-off
       profile.";
    uses upstream-power-back-off-parameters;
  }
}
