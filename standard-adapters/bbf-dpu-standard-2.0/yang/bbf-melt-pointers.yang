submodule bbf-melt-pointers {
  yang-version 1.1;
  belongs-to bbf-melt {
    prefix bbf-melt;
  }

  import ietf-interfaces {
    prefix if;
  }
  include bbf-melt-base;

  /* PMD Control Definitions */

  include bbf-melt-pmd-control-body;

  /* Profile Definitions */

  include bbf-melt-pmd-profiles;
  include bbf-melt-processing-profiles;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing profiles for Metaliic Line Test (MELT) on supported
     interfaces.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  augment "/if:interfaces/if:interface/bbf-melt:melt" {
    description
      "Data nodes to support the assignment of Metallic Line Test
       (MELT) configuration.";
    leaf pmd-profile {
      type pmd-profile-ref;
      status deprecated;
      description
        "References a Metallic Line Test Physical Medium Dependent
         (MELT-PMD) profile. This method of configuration has been
         deprecated. The 'profile-config' method should instead be
         used.";
    }
    leaf processing-profile {
      if-feature "melt-p";
      type leafref {
        path "/bbf-melt:melt/bbf-melt:profiles/bbf-melt:processing-"
           + "profile/bbf-melt:name";
      }
      status deprecated;
      description
        "References a Metallic Test Processing (MELT-P) profile. This
         method of configuration has been deprecated. The
         'profile-config' method should instead be used.";
    }
    container melt-pmd-control {
      status deprecated;
      description
        "Data nodes to support the Metallic Line Test Physical Medium
         Dependent (MELT-PMD) control object.";
      uses melt-pmd-control {
        status deprecated;
      }
    }
    choice profile-config {
      default "no-profiles-attached";
      description
        "Provides methods attachment of profiles.";
      case no-profiles-attached {
        leaf no-profiles-attached {
          type empty;
          description
            "If present, indicates that no profiles are attached
             to this line.";
        }
      }
      case direct-attachment-mode {
        container direct-attachment-mode {
          description
            "Configuration associated with assigning Metallic Line
             Test (MELT) profiles.";
          leaf pmd-profile {
            type pmd-profile-ref;
            mandatory true;
            description
              "References a Metallic Line Test Physical Medium
               Dependent (MELT-PMD) profile.";
          }
          leaf processing-profile {
            if-feature "melt-p";
            type leafref {
              path "/bbf-melt:melt/bbf-melt:profiles/bbf-melt:"
                 + "processing-profile/bbf-melt:name";
            }
            mandatory true;
            description
              "References a Metallic Test Processing (MELT-P)
               profile.";
          }
        }
      }
    }
  }
}
