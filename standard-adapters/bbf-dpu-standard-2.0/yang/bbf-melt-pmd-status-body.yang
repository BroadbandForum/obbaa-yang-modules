submodule bbf-melt-pmd-status-body {
  yang-version 1.1;
  belongs-to bbf-melt {
    prefix bbf-melt;
  }

  import ietf-yang-types {
    prefix yang;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing the Physical Medium Dependent (PMD) object.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }

  typedef pmd-result {
    type enumeration {
      enum no-measurement-results-available {
        description
          "No measurement results are available when no mesurement
           has been performed yet or after measurement results have
           been deleted.";
      }
      enum measurement-failed-results-invalid {
        description
          "The measurement results are invalid after the most recent
           measurement failed.";
      }
      enum measurement-succeeded-results-valid {
        description
          "The measurement results are valid after the most recent
           measurement succeeded.";
      }
    }
    description
      "The overall results of the Physical Medium Dependent (PMD)
       measurement.";
    reference
      "ITU-T G.996.2 clause E.3.4";
  }

  grouping pmd-status {
    description
      "Status parameters for the Physical Medium Dependent (PMD)
       object.";
    leaf melt-status-c {
      type enumeration {
        enum inactive {
          description
            "The Metallic Line Test (MELT) functionality is
             inactive.";
        }
        enum measurement-ongoing {
          description
            "The measurement is ongoing.";
        }
        enum pit-generation-ongoing {
          description
            "The Pair Identifiation Tone (PIT) is ongoing.";
        }
      }
      description
        "The status of the Metallic Line Test Physical Medium
         Dependent (MELT-PMD) measurement.

         Upon the MELT PMD request triggering a measurement, the
         MELT PMD status shall become 'measurement-ongoing' if
         the measurement is executed.

         Upon the MELT PMD request triggering a Pair Identification
         Tone (PIT) generation, the MELT PMD status shall become
         'pit-ongoing' if the PIT generation is executed.

         Upon abortion or successful completion of the measurement or
         PIT generation, the MELT PMD status shall become 'inactive'
         and the AN/DPU ME shall send a notification to the NMS.";
      reference
        "ITU-T G.996.2 clause E.3.3";
    }
    leaf melt-results-c {
      type pmd-result;
      description
        "The overall results of the Metallic Line Test Physical Medium
         Dependent (MELT-PMD) measurement.";
      reference
        "ITU-T G.996.2 clause E.3.4";
    }
    leaf results-timestamp {
      type yang:date-and-time;
      description
        "The time stamp contains the time when results of last
         measurement test were stored.";
      reference
        "ITU-T G.996.2 clause E.2.2.5";
    }
  }
}
