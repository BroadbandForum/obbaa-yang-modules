submodule bbf-vdsl-xtu-channel-status-body {
  yang-version 1.1;
  belongs-to bbf-vdsl {
    prefix bbf-vdsl;
  }

  import bbf-yang-types {
    prefix bbf-yang;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, ADTRAN

     PS Leader:   Sowrirajan Padmanabhan, Nokia

     PS Leader:   Joey Boyd, ADTRAN

     WA Director: Sven Ooghe, Nokia

     WA Director: Joey Boyd, ADTRAN";
  description
    "This submodule contains a collection of YANG definitions for
     managing Broadband Forum TR-252i3 clause 6.1.2 xDSL Transceiver 
     Unit (xTU) Channel Status.

     Copyright (c) 2016-2020 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a3; see
     the TR itself for full legal notices.";

  revision 2020-05-11 {
    description
      "Amendment 3 Straw Ballot.
       * Approval Date:    TBD
       * Publication Date: TBD.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping xtu-channel-status {
    description
      "The xDSL Transceiver Unit (xTU) Channel Status object 
       represents current channel status / measurements at a 
       particular xTU.";
    leaf actual-data-rate {
      type bbf-yang:data-rate32-or-undetermined;
      description
        "Actual data rate or expected throughput (ETR). See ITU-T
         G.997.1 clause 7.5.2.1 for a detailed definition.";
      reference
        "ITU-T G.997.1 clause 7.5.2.1 Actual data rate";
    }
    leaf previous-data-rate {
      type bbf-yang:data-rate32-or-undetermined;
      description
        "Previous data rate or expected throughput (ETR). This
         parameter reports the previous net data rate or ETR the
         bearer channel was operating at just before the latest
         net data rate or ETR change event occurred, excluding
         all transitions between L0 state and L1 or L2 states.
         See ITU-T G.997.1 clause 7.5.2.2 for a detailed
         definition.";
      reference
        "ITU-T G.997.1 clause 7.5.2.2 Previous data rate";
    }
    leaf actual-delay {
      type uint16;
      units "milliseconds";
      description
        "Actual delay due to interleaving or retransmission. See
         ITU-T G.997.1 clause 7.5.2.3 for a detailed definition.
         The actual delay is coded in ms (rounded to the nearest
         ms).";
      reference
        "ITU-T G.997.1 clause 7.5.2.3 Actual delay";
    }
    leaf actual-inp {
      type uint16 {
        range "0..2047";
      }
      units "0.1 DMT symbols";
      description
        "Actual Impulse Noise Protection (ACTINP). See ITU-T
         G.997.1 clause 7.5.2.4 for a detailed definition. The
         value is coded in fractions of DMT symbols with a
         granularity of 0.1 symbols.
         If retransmission is not used in a given transmit direction,
         this parameter reports the interleaved error correction
         INP. For ITU-T G993.2, the special value 255
         indicates an ACTINP of 25.5 or higher.
         If retransmission is used in a given transmit direction,
         this parameter reports the actual impulse noise protection
         (INP) against SHINE (under specific conditions detailed in
         [ITU T G.998.4]) on the bearer channel in the L0 state.
         The special value 2047 indicates an ACTINP of 204.7
         or higher.";
      reference
        "ITU-T G.997.1 clause 7.5.2.4 Actual impulse noise
         protection (ACTINP)";
    }
    leaf inpreport {
      type enumeration {
        enum 0 {
          description
            "If set to 0, the Actual Impulse Noise Protection (ACTINP)
             is computed according to the INP_no_erasure formula
             (see clause 9.6 of [ITU-T G.993.2]).";
        }
        enum 1 {
          description
            "If set to 1, the Actual Impulse Noise Protection (ACTINP)
             is the value estimated by the xDSL Transceiver Unit (xTU)
             receiver.";
        }
      }
      description
        "This parameter reports the method used to compute the
         Actual Impulse Noise Protection (ACTINP). If set to 0, the
         ACTINP is computed according to the INP_no_erasure formula
         (see clause 9.6 of [ITU-T G.993.2]). If set to 1, the ACTINP
         is the value estimated by the xDSL Transceiver Unit (xTU) 
         receiver.";
      reference
        "ITU-T G.997.1 clause 7.5.2.5 Impulse noise protection
         reporting mode (INPREPORT)";
    }
    leaf nfec {
      type uint8 {
        range "0..255";
      }
      units "bytes";
      description
        "This parameter reports the actual Reed-Solomon codeword
         size used in the latency path in which the bearer
         channel is transported. The value is coded in bytes. It
         ranges from 0 to 255.";
      reference
        "ITU-T G.997.1 clause 7.5.2.6.1 Actual size of
         Reed-Solomon codeword (NFEC)";
    }
    leaf rfec {
      type uint8 {
        range "0..16";
      }
      units "bytes";
      description
        "This parameter reports the actual number of Reed-Solomon
         redundancy bytes per codeword used in the latency path
         in which the bearer channel is transported. The value is
         coded in bytes. It ranges from 0 to 16. The value 0
         indicates no Reed-Solomon coding.";
      reference
        "ITU-T G.997.1 clause 7.5.2.6.2 Actual number of
         Reed-Solomon redundancy bytes (RFEC)";
    }
    leaf actual-number-of-bits-per-symbol {
      type uint32 {
        range "0..131071";
      }
      units "bits";
      description
        "This parameter reports the actual number of bits per
         symbol assigned to the latency path in which the bearer
         channel is transported. This value does not include
         trellis overhead. The value is coded in bits. It ranges
         from 0 to 131071.";
      reference
        "ITU-T G.997.1 clause 7.5.2.6.3 Actual number of bits per
         symbol (LSYMB)";
    }
    leaf actual-interleaving-depth {
      type uint16 {
        range "1..4096";
      }
      description
        "This parameter reports the actual depth of the
         interleaver used in the latency path in which the bearer
         channel is transported. The value ranges from 1 to 4096
         in steps of 1. The value 1 indicates no interleaving.";
      reference
        "ITU-T G.997.1 clause 7.5.2.6.4 Actual interleaving depth
         (INTLVDEPTH)";
    }
    leaf actual-interleaving-block-length {
      type uint8 {
        range "4..255";
      }
      description
        "This parameter reports the actual block length of the
         interleaver used in the latency path in which the bearer
         channel is transported. The value ranges from 4 to 255
         in steps of 1.";
      reference
        "ITU-T G.997.1 clause 7.5.2.6.5 Actual interleaving block
         length (INTLVBLOCK)";
    }
    leaf actual-latency-path {
      type uint8 {
        range "0..3";
      }
      description
        "This parameter reports the index of the actual latency
         path in which the bearer is transported. The valid
         values are 0, 1, 2, 3.";
      reference
        "ITU-T G.997.1 clause 7.5.2.7 Actual latency path
         (LPATH)";
    }
    leaf fec-codewords-per-dtu {
      type uint8 {
        range "1..64";
      }
      description
        "This parameter reports the number of Reed-Solomon fec
         codewords per Data Transfer Unit (DTU), used in the latency
         path in which the bearer channel is transported, also known
         as the Q parameter. This parameter only applies to systems
         supporting ITU-T G.998.4.";
      reference
        "ITU-T G.997.1 clause 7.5.2.6.6 (RSPERDTU) and ITU-T
         G.998.4 clause 9.4.3.";
    }
  }

  // end grouping xtu-channel-status

  grouping actual-ndr-inp-rein {
    description
      "This grouping contains Actual Net Data Rate (ACTNDR) and
       Actual Net Data Rate against Repetitive Electrical Impulse
       Noise (ACTINP-REIN).";
    leaf actual-ndr {
      type bbf-yang:data-rate32-or-undetermined;
      description
        "This parameter is independent of whether
         retransmission is used or not in a given transmit
         direction.
         - In L0 state, this parameter reports the net data
         rate (as specified in [ITU-T G.992.3], [ITU-T G.992.5]
         or [ITU-T G.993.2]) at which the bearer channel is
         operating.
         - In L2 state, the parameter contains the net data
         rate (as specified in [ITU-T G.992.3], [ITU-T G.992.5]
         or [ITU-T G.993.2]) in the previous L0 state.
         The data rate is coded in steps of 1,000 bit/s.";
      reference
        "ITU-T G.997.1 clause 7.5.2.8 Actual net data rate
         (ACTNDR)";
    }
    leaf actual-inp-against-rein {
      type uint8 {
        range "0..255";
      }
      units "0.1 DMT symbols";
      description
        "If retransmission is used in a given transmit
         direction, this parameter reports the actual Impulse
         Noise Protection (INP) against Repetitive Electrical Impulse
         Noise (ACTINP-REIN) (under specific conditions detailed in
         [ITU T G.998.4]) on the bearer channel in the L0 state. In
         the L2 state, the parameter contains the INP in the previous
         L0 state. The value is coded in fractions of DMT symbols with
         a granularity of 0.1 symbols.
         The range is from 0 to 25.4. A special value of 255
         indicates an ACTINP_REIN of 25.5 or higher.";
      reference
        "7.5.2.9 Actual impulse noise protection against REIN
         (ACTINP_REIN)";
    }
  }

  // end grouping actual-ndr-inp-rein
}
