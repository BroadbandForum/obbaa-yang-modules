module bbf-obbaa-tp-types {
  yang-version 1.1;
  namespace "urn:bbf:yang:obbaa:tp-types";
  prefix bbf-tpt;

  organization
    "Broadband Forum <https://www.broadband-forum.org>
     Common YANG Work Area";

  contact
    "Comments or questions about this Broadband Forum YANG module
     should be directed to <mailto:obbaa-leaders@broadband-forum.org>.
    ";

  description
    "This module contains a set of termination point type definitions that
     are applicable to the NBI Model of BAA.

     Copyright 2022 Broadband Forum

     Licensed under the Apache License, Version 2.0 (the \"License\");
     you may not use this file except in compliance with the License.
     You may obtain a copy of the License at

     http://www.apache.org/licenses/LICENSE-2.0
     Unless required by applicable law or agreed to in writing, software
     distributed under the License is distributed on an \"AS IS\" BASIS,
     WITHOUT WARRANTIES OR CONDITIONS OF ANY KIND, either express or implied.
     See the License for the specific language governing permissions and
     limitations under the License.
     ";

  revision 2021-09-14 {
    description
      "Initial revision.";
  }

  identity tp-type {
    description
      "Base identity from which specific termination point types are derived.";
  }

  identity uni {
    base tp-type;
    description
      "A user-side network interface type of termination point.";
  }

  identity nni {
    base tp-type;
    description
      "A network-side network interface type of termination point.";
  }

  identity v-nni {
    base tp-type;
    description
      "A virtual network-side network interface type of termination point.";
  }

  identity pon {
    base tp-type;
    description
      "A PON type of termination point.";
  }

  identity l2-v-uni {
    base tp-type;
    description
      "Layer 2 virtual user-side network interface type of termination point.";
  }

  identity l2-v-nni {
    base tp-type;
    description
      "Layer 2 virtual network-side network interface type of termination point.";
  }

  identity l2-svlan {
    base tp-type;
    description
      "Layer 2 network-side forwarding VLAN type of termination point.";
  }
}
