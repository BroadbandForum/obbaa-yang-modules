module bbf-obbaa-nt-service-profile {
  yang-version 1.1;
  namespace "urn:bbf:yang:obbaa:nt-service-profile";
  prefix bbf-nt-srv-prof;

  import bbf-obbaa-l2-access-common {
    prefix bbf-l2acc-c;
  }

  organization
    "Broadband Forum <https://www.broadband-forum.org>";

  contact
    "Comments or questions about this Broadband Forum YANG module
     should be directed to <mailto:obbaa-leaders@broadband-forum.org>.
    ";

  description
    "This module contains a collection of service profile definitions that
     are applicable to the NBI Model of BAA, and simplify the L2 service
     configuration.

     Copyright 2022 Broadband Forum

     Licensed under the Apache License, Version 2.0 (the \"License\");
     you may not use this file except in compliance with the License.
     You may obtain a copy of the License at

     http://www.apache.org/licenses/LICENSE-2.0
     Unless required by applicable law or agreed to in writing, software
     distributed under the License is distributed on an \"AS IS\" BASIS,
     WITHOUT WARRANTIES OR CONDITIONS OF ANY KIND, either express or implied.
     See the License for the specific language governing permissions and
     limitations under the License.
     ";

  revision 2021-09-14 {
    description
      "Initial revision.";
    reference
      "";
  }

  typedef service-profile-ref {
    type leafref {
      path
        "/bbf-nt-srv-prof:service-profiles/bbf-nt-srv-prof:service-profile/bbf-nt-srv-prof:name";
    }
    description
      "A reference to a service profile.";
  }

  container service-profiles {
    description
      "All config data for service profile.";
    list service-profile {
      key "name";
      description
        "List of service profiles.";
      leaf name {
        type string {
          length "1..32";
        }
        description
          "The service profile name.";
      }
      container ports {
        description
          "All config data for ports.";
        list port {
          key "name";
          description
            "List of the port attribute.";
          leaf name {
            type string {
              length "1..64";
            }
            description
              "Indicates the name of the port.";
          }
          container port-vlans {
            description
              "All config data for port vlan.";
            list port-vlan {
              key "name";
              description
                "This is used to add a user-side port on the network termination to a VLAN";
              leaf name {
                type leafref {
                  path
                    "/bbf-l2acc-c:vlan-translation-profiles/bbf-l2acc-c:vlan-translation-profile/bbf-l2acc-c:name";
                }
                description
                  "Name of the port VLAN.";
              }
            }
          }
        }
      }
    }
  }
}
