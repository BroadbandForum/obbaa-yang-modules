module bbf-obbaa-pmaa-onu-types {
  yang-version 1.1;
  namespace "urn:bbf:yang:obbaa:pmaa-onu-types";
  prefix baa-pmaa-onu-types;
  
  organization
    "Broadband Forum <https://www.broadband-forum.org>";

  contact
    "Comments or questions about this Broadband Forum YANG module
     should be directed to <mailto:obbaa-leaders@broadband-forum.org>.
    ";

  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).
     
     Specifically, this module contains common type definitions for 
     use in the Persistent Management Agent Aggregator (PMAA).
     
     Copyright 2022 Broadband Forum
     
     Licensed under the Apache License, Version 2.0 (the \"License\");
     you may not use this file except in compliance with the License.
     You may obtain a copy of the License at
     
     http://www.apache.org/licenses/LICENSE-2.0
     Unless required by applicable law or agreed to in writing, 
     software distributed under the License is distributed on an \"AS 
     IS\" BASIS, WITHOUT WARRANTIES OR CONDITIONS OF ANY KIND, either
     express or implied. See the License for the specific language 
     governing permissions and limitations under the License.";
  
  revision 2022-05-24 {
    description
      "Initial revision.";
    reference
      "https://obbaa.broadband-forum.org/";
  }
  
  identity onu-authentication-notification-base {
    description
      "Base type for ONU authentication related notifications 
       generated by the PMAA. This identity is abstract and SHOULD NOT
       be used directly in notifications.";
  }

  identity onu-not-authenticated {
    base onu-authentication-notification-base;
    description
      "Indicates that the ONU in the PMAA is not authenticated.
       This can be for instance because the ONU is not connected 
       to the xPON Network or that, while present on an OLT, the 
       ONU could not be authenticated neither by the OLT nor the 
       PMAA.";
    reference
      "WT-489";
  }
  
  identity "onu-not-authenticated-not-present" { 
    base onu-not-authenticated;
    description
      "Indicates that the ONU is not authenticated because 
       it is not connected to the xPON Network."; 
    reference
      "WT-489";
  }
      
  identity "onu-authentication-failed" {
    base onu-not-authenticated;
    description
      "Indicates that the ONU while connected to an OLT could 
       not be authenticated by the OLT nor the PMAA.";
    reference
      "WT-489";
  }
  
  identity "onu-authenticated" {
    base onu-authentication-notification-base;
    description
      "Indicates that the ONU in the PMAA is connected to the 
       xPON Network and is authenticated. 
       This specific identity does not provide information about 
       the ONU Management mode.";
  }

  identity "onu-mgt-mode-ok" {
    base onu-authenticated;
    description
      "Indicates that the ONU in the PMAA is authenticated and 
       its management mode is determined."; 
  }
    
  identity "onu-going-eomci" { 
    base onu-mgt-mode-ok;
    description
      "Indicates that the ONU in the PMAA is authenticated and 
      its management mode is determined to be eOMCI.";
  }
   
  identity "onu-going-vomci" { 
    base onu-mgt-mode-ok;
    description
      "Indicates that the ONU in the PMAA is authenticated and 
       its management mode is determined to be vOMCI.";
  }
  

  identity "onu-mgt-mode-error" {
    base onu-authenticated;
    description
      "Indicates that the ONU in the PMAA is authenticated but  
       its management mode could not be determined or is 
       associated with some error."; 
  }
   
  identity "onu-mgt-mode-mismatch-olt-pmaa" { 
    base onu-mgt-mode-error;
    description
      "Indicates that the ONU in the PMAA is authenticated but  
       its management mode is conflicting between the OLT and 
       the PMAA."; 
  }
  
  identity "eomci-per-olt-vomci-per-pmaa" {
    base onu-mgt-mode-mismatch-olt-pmaa;
    description
      "Indicates that the ONU in the PMAA is authenticated but  
       the OLT determines eOMCI while the PMAA determines 
       vOMCI."; 
  }
   
  identity "vomci-per-olt-eomci-per-pmaa" {
    base onu-mgt-mode-mismatch-olt-pmaa;
    description
      "Indicates that the ONU in the PMAA is authenticated but  
       the OLT determines vOMCI while the PMAA determines 
       eOMCI."; 
  }
  
  identity "onu-name-mismatch-olt-pmaa" {
    base onu-mgt-mode-error;
    description
      "Indicates that the ONU in the PMAA is authenticated and   
       its management mode is determined but there is a conflict 
       between the onu device name as known in the PMAA and the 
       onu-name as known in corresponding vANI in the OLT."; 
  }
  
  identity "vomci-but-pmaa-missing-data" {
    base onu-mgt-mode-error;
    description
      "Indicates that the ONU in the PMAA is authenticated and   
       its management mode is determined to be vOMCI but the
       PMAA is missing data to manage the ONU via vOMCI.";
  }
   
  identity "onu-mgt-mode-undetermined-error" { 
    base onu-mgt-mode-error;
    description
      "Indicates that the ONU in the PMAA is authenticated but   
       its management mode is undetermined due to some error."; 
  }   

  identity action-error-tag {
    description
      "A base identity for defining failures with the invocation of an
      onu-authentication-report action from the Management Plane to 
      the OLT.";
  }

  identity parameter-error {
    base action-error-tag;
    description
      "Parameter error.";
  }

  identity onu-not-present {
    base parameter-error;
    description
      "Indicates what the Optical Network Unit (ONU) is
       not present or not present anymore on the channel 
       termination.";
  }

  identity onu-management-mode-mismatch-with-v-ani {
    base parameter-error;
    description
      "Indicates that the required ONU management mode 
       conflicts with an explicitely configured 
       'planned-onu-magement-mode' on the vANI.";
  }

  identity onu-name-mismatch-with-v-ani {
    base parameter-error;
    description
      "Indicates that the provided 'onu-name' 
       conflicts with an explicitely configured 
       'onu-name' on the vANI.";
  }

  identity undetermined-error {
    base action-error-tag;
    description
      "Undetermined error.";
  }
}
